module acc-protection-group {
    yang-version 1.1;
    namespace "urn:ccsa:yang:acc-protection-group";
    prefix acc-pg;

    revision 2021-09-24 {
        description "uniform date for motn";
    }

    /*
    * common types
    */
    typedef protection-type {
        type enumeration {
            enum odu-sncp-i {
                value 0;
            }
            enum odu-sncp-s {
                value 1;
            }
            enum vc-sncp {
                value 2;
            }
            enum och-1-plus-1 {
                value 3;
            }
            enum msp-1-plus-1 {
                value 4;
            }
            enum lag {
                value 5;
            }
            enum no-protection {
                value 6;
            }
            enum osu-sncp-i {
                value 7;
            }
            enum osu-sncp-n {
                value 8;
            }
            enum osu-sncp-s {
                value 9;
            }
            enum odu-sncp-n {
                value 10;
            }
            enum lag-load-blancing {
                value 11;
                description "ETH layer LAG load blancing";
            }
        }
    }

    typedef protection-type-eq-pg{
        type enumeration{
	    enum control-1-plus-1{
	        value 0;
	        description "control-1-plus-1";
	    }
	    enum cross-connect-1-plus-1{
	        value 1;
                description "cross connect 1-plus-1";
            }
            enum control-cross-connect-1-plus-1{
                value 2;
                description "control cross connect-1-plus-1";
	    }
            enum power-1-plus-1{
                value 3;
                description "power-1-plus-1";
	    }
	}
    }


    typedef switch-type {
        type enumeration {
            enum uni-switch {
                value 0;
                description "uni switch";
            }
            enum bi-switch {
                value 1;
                description  "bi switch";
            }
        }
        description
            "switch type";
    }
    typedef sd-trigger {
        type enumeration {
            enum enabled {
                value 0;
                description "sd trigger enabled";
            }
            enum disabled {
                value 1;
                description  "sd trigger disabled";
            }
        }
        description
            "sd-trigger";
    }
    typedef protection-direction {
        type enumeration {
            enum to-primary {
                value 0;
                description "to primary";
            }
            enum to-secondary {
                value 1;
                description "to secondary";
            }
        }
    }
    typedef reversion-mode {
        type enumeration {
            enum revertive {
                value 0;
                description "企标中的是 revertive";
            }
            enum non-revertive {
                value 1;
                description "企标中的是 non-revertive";
            }
        }
    }
   typedef switch-reason {
        type enumeration {
            enum no-switch {
                value 0;
                description "no switch,only for pg";
            }
            enum sf-switch {
                value 1;
                description "SF switch,for pg and eq-pg";
            }
            enum sd-switch {
                value 2;
                description "SD switch,only for pg";
            }
            enum manual-switch {
                value 3;
                description "manual switch,for pg and eq-pg";
            }
            enum force-switch {
                value 4;
                description "force switch,only for pg";
            }
            enum cleared {
                value 5;
                description "cleared,for pg and eq-pg";
            }
            enum wait-for-restore {
                value 6;
                description "WTR,only for pg";
            }
            enum lockout {
                value 7;
                description "lockout of protection,only for pg";
            }
        }
    }


    /*
    * groupings
    */
    grouping pg {
        description
            "pg";
        leaf pg-id {
            mandatory true;
            type uint16;
        }
        leaf protection-type {
            mandatory true;
            type protection-type;
            description "protection type";
        }
        leaf reversion-mode {
            mandatory true;
            type reversion-mode;
            description  "reversion mode";
        }
        leaf tcm {
            type uint16;
        }
        leaf switch-type {
            mandatory true;
            type switch-type;
            description "switch type";
        }

        leaf switch-reason {
            type switch-reason;
            config false;
            description "switch reason, default NO SWITCH";
        }
        leaf protection-direction {
            type protection-direction;
            config false;
            description  "protection direction";
        }
        leaf hold-off {
            type uint32;
            units ms;
            default 0;
            description  "hold off time";
        }
        leaf wait-to-restore-time {
            mandatory true;
            type uint64;
            units seconds;
            description "wait to restore time";
        }
        leaf sd-trigger {
            type sd-trigger;
            description "sd protection";
        }
        leaf primary-port {
            mandatory true;
            type string;
            description "primary port CTP/FTP/PTP,不同业务对应不同的端口类型";
        }
        leaf secondary-port {
            mandatory true;
            type string;
            description "secondary port PTP/FTP/CTP,不同业务对应不同的端口类型";
        }
        leaf selected-port {
            mandatory true;
            type string;
            config false;
            description "selected port PTP/FTP/CTP,不同业务对应不同的端口类型";
        }
    }

 grouping eq-pg{
	description "eq-pg";
	leaf pg-id{
	    mandatory true;
	    type uint16;
        }
	leaf protection-type{
	    mandatory true;
	    type protection-type-eq-pg;
	}
	leaf switch-reason{
	    type switch-reason;
	}
	leaf protection-direction{
	    mandatory true;
	    type protection-direction;
	}
	leaf primary-eq{
	    mandatory true;
	    config false;
	    type string;
	}
	leaf secondary-eq{
	    mandatory true;
            config false;
            type string;
	}
        leaf selected-eq{
            mandatory true;
            config false;
            type string;
	}
    }
    /*
    * the data tree
    */
    container pgs {
        list pg {
            key 'pg-id';
            uses pg;
            description "pg";
        }
        description "pgs";
    }

    container eq-pgs {
        list eq-pg {
            key 'pg-id';
            uses eq-pg;
        }
        description "eq-pgs";
    }

   notification protection-switch-notification {
        leaf protection-switch-serial-no {
            mandatory true;
            type uint64;
        }
		choice pg-or-eqpg {
	        case pg {
			    container pg {
				    uses pg;
				}
			}
			case eqpg {
			    container eq-pg {
				    uses eq-pg;
				}
			}
		}
        description "protection switch notification";
    }
    /*
    * operations
    */
    rpc perform-protection-command {
        description
            "protection";
        input {
            leaf pg-id {
                mandatory true;
                type uint64;
                description  "pg id";
            }

            leaf protection-command {
                mandatory true;
                type switch-reason;
                description "protection command";
            }

            leaf protection-direction {
                mandatory true;
                type protection-direction;
                description "protection direction";
            }
        }
    }

    rpc perform-eq-protection-command {
        description
            "eq-protection";
        input {
            leaf pg-id {
                mandatory true;
                type uint64;
                description  "eqpg-id";
            }

            leaf protection-command {
                mandatory true;
                type switch-reason;
                description "eq protection command";
            }

            leaf protection-direction {
                mandatory true;
                type protection-direction;
                description "eq protection direction";
            }
        }
    }
}
