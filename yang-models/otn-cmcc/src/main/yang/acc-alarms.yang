module acc-alarms {
    yang-version 1.1;
    namespace "urn:ccsa:yang:acc-alarms";
    prefix acc-alm;

    import ietf-yang-types {
        prefix yang;
    }
    import acc-yang-types {
        prefix acc-type;
    }
  
    organization "xxx";
    contact "xxx";
    description "this module defines an interface for managing alarms.";
    revision 2019-02-13 {
        description "initial revision.";
    }
    /*
    * common types
    */
    typedef alarm-state {
        type enumeration {
            enum start {
                value 0;
                description "alarm-state start";
            }
            enum end {
                value 1;
                description "alarm-state end";
            }
        }
        description "alarm-state";
    }
    typedef perceived-severity {
        type enumeration {
            enum critical {
                value 0;
                description "perceived-severity critical";
            }
            enum major {
                value 1;
                description "perceived-severity major";
            }
            enum minor {
                value 2;
                description "perceived-severity minor";
            }
            enum warning {
                value 3;
                description "perceived-severity warning";
            }
        }
        description "perceived-severity";
    }
    /*
    * groupings
    */
    grouping alarm {
        description
            "common parameters for an alarm.";
        leaf alarm-serial-no {
            mandatory true;
            type uint64;
            description "alarm alarm-serial-no";
        }
        leaf object-name {
            mandatory true;
            type string {
                length "1..64";
            }
            description "alarm object-name";
        }
        leaf object-type {
            mandatory true;
            type string {
                length "1..64";
            }
            description "alarm object-type";
        }
        leaf alarm-code {
            mandatory true;
            type string {
                length "1..64";
            }
            description "alarm alarm-code";
        }
        leaf alarm-state {
            mandatory true;
            type alarm-state;
            description "alarm alarm-state";
        }
        leaf perceived-severity {
            mandatory true;
            type perceived-severity;
            description "alarm perceived-severity";
        }
        leaf start-time {
            mandatory true;
            type yang:date-and-time;
            description "alarm start-time";
        }
        leaf end-time {
            type yang:date-and-time;
            description "alarm end-time";
        }
        leaf additional-text {
            type string {
                length "0..512";
            }
            description "alarm additional-text";
        }
    }
    grouping alarms-grouping {
        list alarm {
            key 'alarm-serial-no';
            config false;
            uses alarm;
            description "alarms list";
        }
        description "alarms";
    }

    grouping tca-parameter {
        leaf object-name {
            mandatory true;
            type string {
                length "1..64";
            }
            description "tca-parameter object-name";
        }
        leaf pm-parameter-name {
            mandatory true;
            type string {
                length "1..64";
            }
            description "tca-parameter pm-parameter-name";
        }
        leaf granularity {
            mandatory true;
            type acc-type:granularity;
            description "tca-parameter granularity";
        }
        leaf threshold-type {
            mandatory true;
            type acc-type:threshold-type;
            description "tca-parameter threshold-type";
        }
        leaf object-type {
            mandatory true;
            type string {
                length "1..64";
            }
            description "tca-parameter object-type";
        }
        leaf threshold-value {
            mandatory true;
            type acc-type:real;
            description "tca-parameter threshold-value";
        }
        description "tca-parameter";
    }


    grouping tca {
        leaf tca-serial-no {
            type uint64;
            description "tca tca-serial-no";
        }
        container tca-parameter {
            config false;
            uses tca-parameter;
            description "tca-parameter";
        }
        leaf tca-state {
            mandatory true;
            type alarm-state;
            config false;
            description "tca tca-state";
        }
        leaf current-value {
            mandatory true;
            type acc-type:real;
            config false;
            description "tca current-value";
        }
        leaf start-time {
            mandatory true;
            type yang:date-and-time;
            config false;
            description "tca start-time";
        }
        leaf end-time {
            type yang:date-and-time;
            config false;
            description "tca end-time";
        }
        description "tca";
    }
    grouping tcas-grouping {
        list tca {
            key 'tca-serial-no';
            uses tca;
            description "tcas list";
        }
        description "tcas";
    }
      
    /*
    * the data tree
    */
    container alarms {
        uses alarms-grouping;
        description "alarms container";
    }        
    container tcas {
        uses tcas-grouping;
        description "tcas container";
    }
    container tca-parameters {
        list tca-parameter {
            key 'object-name pm-parameter-name granularity threshold-type';
            uses tca-parameter;
            description "tca-parameter";
        }
    }
    container alarm-mask-states {
        list alarm-mask-state {
            key 'object-name alarm-code';
            min-elements 1;
            leaf object-name {
                type string {
                    length "1..64";
                }
                mandatory true; 
                description "alarm-mask-state object-name";
            }
            leaf alarm-code {
                type string {
                    length "1..64";
                }
                mandatory true;
                description "alarm-mask-state alarm-code";
            }
            leaf object-type {
                type string {
                    length "1..64";
                }
                mandatory true;
                description "alarm-mask-state object-type";
            }
            leaf mask-state {
                type boolean;
                mandatory true;
                description "true is mask";
            }
        }
        description "alarm-mask-states";
    }        

    /*
    * notifications
    */
    notification alarm-notification {
        container alarm {
            uses alarm;
            description "alarm-notification container";
        }
        description "alarm-notification";
    }
    notification tca-notification {
        container tca {
            uses tca;
            description "tca-notification container";
        }
        description "tca-notification";
    }
    /*
    * operations
    */
    rpc get-history-alarms {
        description "get-history-alarms";
        input {
            leaf start-time {
                mandatory true;
                type yang:date-and-time;
                description "start-time";
            }
            leaf end-time {
                mandatory true;
                type yang:date-and-time;
                description "end-time";
            }
        }
        output {
            container alarms {
                uses alarms-grouping;
                description "output alarms";
            }
            container tcas {
                uses tcas-grouping;
                description "output tcas";
            }
        }
    }
}
