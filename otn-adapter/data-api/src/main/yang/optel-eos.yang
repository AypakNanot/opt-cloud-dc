module optel-eos {
    yang-version 1.1;
    namespace "com:optel:yang:api:optel-eos";
    prefix optel-eos;

    import optel-devm {
        prefix optel-devm;
        revision-date "2021-09-27";
    }
    import optel-eth {
        prefix optel-eth;
        revision-date "2021-09-27";
    }
    import optel-sdh {
        prefix optel-sdh;
        revision-date "2021-09-27";
    }
    import optel-connection {
        prefix optel-con;
        revision-date "2021-09-27";
    }
    import optel-otn {
        prefix optel-otn;
        revision-date "2021-09-27";
    }

    import optel-otn-types {
        prefix optel-otn-types;
        revision-date "2021-09-27";
    }

    import optel-protection-group {
        prefix optel-pg;
        revision-date "2021-09-27";
    }
    

    revision 2021-09-27 {
        description
            "Initial revision.";
        reference
            "xxx";
    }

    augment "/optel-devm:ftps/optel-devm:ftp/optel-eth:eth-ftp-pac" {
        when "optel-eth:mapping-type = 'EoS'";
        container vcg-parameters {
            uses optel-sdh:vcg-pac;
            description "Virtual concatenation group";
        }
    }
	
    grouping create-eos-connection-in-grouping{
            uses optel-con:create-connection;
            leaf service-mapping-mode {
                type optel-otn-types:adaptation-type;
                description "基于SDH FTP客户信号类型，STM-1/STM-4=GMP，STM-16/STM-64=CBR_BMP";
            }
            leaf uni-protection-type {
                type optel-pg:protection-type;
                description "default lag";
            }
            container eth-uni {
                leaf uni-ptp-name {
                    type string;
                }
                leaf second-uni-ptp-name {
                    type string;
                    description "可选，用于与客户设备之间建立LAG保护（非负载均衡，单端保护）";
                }
				container client-vlan-spec {
					when "../../service-type = 'EVPL'";
                    uses optel-con:vlan-spec;
                    description "用于客户Vlan与运营商Vlan的匹配，根据客户需求指定vlanType，不带accessAction视为keep";
                }
				container uni-vlan-spec {
					when "../../service-type = 'EVPL'";
                    uses optel-con:vlan-spec;
                    description "可针对client-vlan-spec进行vlan的交换exchange或者添加剥离 pop_push; 或者无client-vlan-spec，单纯push-pop新的vlan；或者不下发";
                }
            }
            uses nni-grouping;
    }

    grouping nni-grouping{
        leaf nni-protection-type {
            type optel-pg:protection-type;
        }
        leaf nni-tcm {
            type uint16;
            description "when nni-protection-type = 'snc-s', needs to be issued to present the nni tcm of both work path and protection path";
        }
        container primary-nni {
            uses optel-otn:nni;
			description "ptp是ODU层协议时，nni参数中的nni-ts-detail、adaptation-type、odu-signal-type、switch-capability这几个参数必填，否则不用填";
            container ftp-client-vlan-spec {
                uses optel-con:vlan-spec;
                description "";
            }
            container ftp-vlan-spec {
                uses optel-con:vlan-spec;
                description "EVPL必须下发，对于其他业务可选，accessAction=PUSH_POP";
            }
            leaf tpid {
                type optel-eth:tpid-difinition;
            }
        }
        container secondary-nni {
            uses optel-otn:nni;
			description "ptp是ODU层协议时，nni参数中的nni-ts-detail、adaptation-type、odu-signal-type、switch-capability这几个参数必填,否则不用填";
            container ftp-client-vlan-spec {
                uses optel-con:vlan-spec;
                description "";
            }
            container ftp-vlan-spec {
                uses optel-con:vlan-spec;
                description "EVPL必须下发，对于其他业务可选，accessAction=PUSH_POP";
            }
            /** 2024-08-01: CTC 支持，CMCC 此结构不支持，但均未实现 */
            leaf tpid {
                type optel-eth:tpid-difinition;
            }
        }

        container eos-pac {
            leaf sdh-signal-type {
                type optel-otn-types:client-signal-type;
            }
            leaf vc-type {
                mandatory true;
                type optel-otn-types:switch-type;
            }
            leaf-list mapping-path {
                min-elements 1;
                type string {
                    length "1..64";
                }
            }
            leaf sdh-signal-type-protect {
                type optel-otn-types:client-signal-type;
            }
            leaf-list mapping-path-protect {
                type string {
                    length "1..64";
                }
            }
            leaf lcas {
                type boolean;
                default false;
            }
            leaf hold-off {
                type uint32;
                default 0;
                description "unit: ms";
            }
            leaf wtr {
                type uint32;
                default 300;
                description "unit: s";
            }
            leaf tsd {
                type boolean;
                default false;
            }
			description "EoS属性";
        }
        container multi-nni-pac{
            list nnis{
                key 'nni-ptp-name nni-ts-detail vcg-key';
                uses multi-nni-grouping;
            }
            description "多路径业务时,传入此参数。此时primary-nni和secondary-nni不填";
        }
        container multi-secondary-nni {
            list secondary-nnis {
                key 'nni-ptp-name nni-ts-detail vcg-key';
                uses multi-nni-grouping;
                leaf nni-protection-type {
                   type optel-pg:protection-type;
                   description "指定保护类型";
                }
                container primary-attr {
                    leaf nni-ptp-name {
                        type string{
                           length "1..64";
                        }
                    }
                    leaf nni-ts-detail {
                        type string{
                           length "1..64";
                        }
                    }
                    leaf vcg-key {
                        type string {
                            length "1..64";
                        }
                        description "填VC占用列表中的第一个mappingPath值";
                    }
                    description "指定被保护的主用信息";
                }
            }
            description "用于多路径业务备用属性配置。可选";
         }
         container lcas-attr {
             uses lcas-attr-grouping;
             description "用于多路径业务的LCAS属性参数。当配置多路径业务时必填，否则不填。";
         }
		 container multi-svlan-attr{
			container ftp-client-vlan-spec {
				 uses optel-con:vlan-spec;
				 description "";
			 }
			 container ftp-vlan-spec {
				 uses optel-con:vlan-spec;
				 description "当需要打上或剖离SVLAN标签的EVPL业务时，必须下发，对于其他业务可选，accessAction=PUSH_POP";
			 }	
			 leaf tpid {
				 type optel-eth:tpid-difinition;
			 }
			 description "用于多路径业务的S-VLAN属性参数。当配置多路径业务时可选";
		 }
    }

    grouping multi-nni-grouping {
         uses optel-otn:nni;
         leaf sdh-signal-type {
             type optel-otn-types:client-signal-type;
         }
         leaf vc-type {
             mandatory true;
             type optel-otn-types:switch-type;
         }
         leaf vcg-key {
             type string {
                 length "1..64";
             }
             description "填VC占用列表中的第一个mappingPath值";
         }
         leaf-list mapping-path {
             min-elements 1;
             type string {
                 length "1..64";
             }
         }
         description "多路径线路侧参数,ptp是ODU层协议时，nni参数中的nni-ts-detail、adaptation-type、odu-signal-type、switch-capability这几个参数必填，否侧除nni-ts-detail固定填字符串“0”外，其它参数都不用填";
    }

    grouping lcas-attr-grouping{
         leaf lcas {
              type boolean;
              default false;
          }
          leaf hold-off {
              type uint32;
              default 0;
              description "unit: ms";
          }
          leaf wtr {
              type uint32;
              default 300;
              description "unit: s";
          }
          leaf tsd {
              type boolean;
              default false;
          }
    }
    rpc create-eos-connection {
        input {
            uses create-eos-connection-in-grouping;
        }
        output {
            uses create-eos-connection-out-grouping;
        }
    }
    grouping create-eos-connection-out-grouping {
            container connection {
                uses optel-con:connection;
            }
            container create-component {
                leaf-list vc-connection-name {
                    type string;
		    min-elements 0;
                }
                leaf-list ftp-name {
                    type string {
                        length "1..64";
                    }
                }
                leaf-list ctp-name {
                    type string {
                        length "1..64";
                    }
                }
            }
    }

    grouping modify-vcg-connection-capacity-in-grouping{
            leaf eth-ftp-name {
                mandatory true;
                type string {
                    length "1..64";
                }
                description
                    "The name of eth ftp name.";
            }
            leaf sdh-ftp-name {
                mandatory true;
                type string {
                    length "1..64";
                }
                description
                    "The name of sdh ftp name.";
            }
            leaf sdh-protect-ftp-name {
                type string {
                    length "1..64";
                }
                description
                    "The name of the protect sdh ftp name.";
            }
            leaf-list mapping-path {
                min-elements 1;
                type string {
                    length "1..64";
                }
                description
                    "The mapping path list.";
            }
            leaf-list mapping-path-protected {
                type string {
                    length "1..64";
                }
                description
                    "The protected mapping path list.";
            }

    }
    rpc modify-vcg-connection-capacity {
        input {
            uses modify-vcg-connection-capacity-in-grouping;
        }
        output {
            leaf-list connection-name {
                type string;
            }
            leaf-list ctp-name {
                type string {
                    length "1..64";
                }
            }
        }
    }
}
