module miniotn-rpc {

  yang-version "1";

    // namespace
  namespace "urn:cmcc:yang:rpc";

  prefix "mo-rpc";

  // import 
  import openconfig-types { prefix oc-types;revision-date "2023-04-26"; }
  import openconfig-yang-types { prefix oc-yang;revision-date "2018-11-21"; }
  import openconfig-platform { prefix oc-platform;revision-date "2023-04-26"; }
  import openconfig-extensions { prefix oc-ext;revision-date "2018-10-17"; }
  import openconfig-transport-types { prefix oc-opt-types;revision-date "2023-04-26"; }
  import ietf-yang-types { prefix yang; }
  import openconfig-platform-types { prefix oc-platform-types;revision-date "2023-04-26"; }  
  import miniotn-performance-types {prefix mo-performance-types;revision-date "2023-04-26";}
  import miniotn-alarms {prefix mo-alarms;revision-date "2023-04-26";}
  import miniotn-tcas {prefix mo-tcas;revision-date "2023-04-26";}
  // meta
   organization "Cmcc minOTN working group";

   contact
    "";

  description
    "This YANG module contains all RPCs for OLS systems.
       This module includes all RPCs usable by NETCONF.";
  
  oc-ext:openconfig-version "1.7.2";

  revision "2023-04-26" {
    description
      "Initial release for MinOTN.";
    reference "1.0.0";
  }

  // typedef statements 

  typedef rpc-result {
    type enumeration {
      enum SUCCESS {
        value 0;
        description
        "The RPC action is success";
      }
      enum FAIL {
        value 1;
        description
        "The RPC action is fail";
      }     
    }    
  }
  
  typedef file-type {
    type enumeration {
      enum data {
        description "data";
      }
      enum upgrade {
        description "upgrade";
      }
    }
  }
  
  typedef download-msg-type {
    type enumeration {
      enum 0-success {
        description
          "success";
      }
      enum 100-socket-fail {
        description
          "socket-fail";
      }
      enum 110-auth-fail {
        description
          "auth-fail";
      }
      enum 120-file-not-exist {
        description
          "file-not-exist";
      }
      enum 130-timeout {
        description
          "timeout";
      }
      enum 140-validate-fail {
        description
          "validate-fail";
      }
      enum 150-file-type-mismatch {
        description
          "file-type-mismatch";
      }
      enum 999-custom {
        description
          "custom";
      }
    }
  }
  
  typedef upload-msg-type {
    type enumeration {
      enum 0-success {
        description
          "success";
      }
      enum 100-socket-fail {
        description
          "socket-fail";
      }
      enum 110-auth-fail {
        description
          "auth-fail";
      }
      enum 130-timeout {
        description
          "timeout";
      }
      enum 150-file-type-mismatch {
        description
          "file-type-mismatch";
      }
      enum 999-custom {
        description
          "custom";
      }
    }
  }

  // grouping statements 

  // rpc statements

  rpc reboot {
    description 
       "Reboot the specific component, i.e. card, transceiver";
      input {
        leaf component-name {
          type leafref {
            path "/oc-platform:components/oc-platform:component/" +
             "oc-platform:name";
          }
          description
             "target reboot components";
        }       

        leaf reboot-type {
          type enumeration {
            enum warm { 
              description "warm reboot";
            }
            enum cold { 
              description "cold reboot";
            }
          }
          description 
            "Reboot type";
        }
      }
      output {
        leaf reboot-result {
          type rpc-result;
          description 
            "Result of the reboot operation";
        }
      }
  }

   
  //rpc switch olp
  rpc switch-olp {
    description 
       "Manual switch the aps to the desired port";
      input {
        
        leaf name {
          type leafref  {
            path "/oc-platform:components/oc-platform:component/" +
             "oc-platform:name";
          }
          description
             "target aps name";
        }  
      
        leaf switch-to-port {
          type enumeration {
            enum PRIMARY {
              description
                "manual switch the OLP to the primary line port";
            }
            enum SECONDARY {
              description
                "manual switch the OLP to the secondary line port";
            }
          }
          description
            "manual set the optical switch to a port";
        }
      }

      output {
        leaf switch-olp-result {
          type rpc-result;
          description 
            "Result of the switch olp operation";
        }
      }
  }
  

    // rpc set-datetime
  rpc set-datetime {
    description 
       "Set equipments' datetime.";
      input {
        leaf datetime {
          type yang:date-and-time;
          description
             "Target datetime to be set";
        }       
      }
      output {
        leaf set-datetime-result {
          type rpc-result;
          description 
            "Result of the set operation";
        }
      }
  }
  
  //rpc get oduk delay
  rpc get-oduk-delay {
    description 
       "Get delay of ODUk.";
      input {
        leaf index {
          type uint32;
          description
             "The index of logical channel(ODU)";
        }  

        leaf delay-test-times {
          type uint32;
          default 10;
          description
             "Measurement repeated times.";
        }  
      }
      output {
        leaf get-delay-result {
          type rpc-result;
          description 
            "Result of the set operation";
        }
        
        container delay-data-value {
          uses oc-opt-types:avg-min-max-instant-stats-precision2-ns;
          description
             "Test results of ODUk delay measurement";
        }   
      }
  }

  //rpc download file
  rpc download-file {
    description 
      "download file";
      input {
        leaf file-type {
          type file-type; 
          description 
            "file-type";
        }
        leaf file-name {
          type string;
          description
            "file name";
        }
        leaf path {
          type string;
          description
            "[sftp]://hostname/directorypath/filename";
        }
        leaf username {
          type string;
          description
            "username";
        }   
        leaf password {
          type string;
          description
            "password";
        }   
      }
      output {
        leaf result {
          type rpc-result;
          description 
            "Result of download file";
        }
        leaf msg {
          type download-msg-type;
          description
            "fail reason";
        }
      }  
  }

  //rpc upload file
  rpc upload-file {
    description 
      "upload file";
      input {
        leaf path {
          type string;
          description
            "path";
        }
        leaf file-type {
          type enumeration {
            enum data {
              value 0;
            }
            enum log {
              value 1;
            }
          }
        }
        leaf file-name {
          type string;
          description
            "file name";
        }
        leaf username {
          type string;
          description
            "username";
        }   
        leaf password {
          type string;
          description
            "password";
        }   
      }
      output {
        leaf result {
          type rpc-result;
          description 
            "Result of upload file";
        }
        leaf msg {
          type upload-msg-type;
          description
            "fail reason";
        }
        leaf md5 {
          type string;
          description
            "md5";
        }
        leaf file-name {
          type string;
          description
            "real file-name";
        }
      }
  }
  
  //rpc get-file-list
  rpc get-file-list {
    input {
      leaf file-type {
        type enumeration {
          enum data {
            value 0;
          }
          enum upgrade {
            value 1;
          }
          enum log {
            value 2;
          }
          enum all {
            value 3;
            description 
              "all file type";
          }
        }
      }
    }
    output {
      leaf result {
          type rpc-result;
           description 
            "Result of upload file";
        }
      leaf msg {
        type string;
      }     
      list file-names {
        key 'file-name';
        leaf file-name {
          type string;
        }
      }  
    }         
  }
  
  //rpc delete file
  rpc delete-file {
    description 
      "delete file";
      input {
        leaf file-name {
          type string;
          description
            "file name";
        }
        leaf file-type {
          type file-type;
          description
            "file type";
        }
      }
      output {
        leaf result {
          type rpc-result;
          description 
            "Result of upload file";
        }
        leaf msg {
          type string;
          description
            "fail reason";
        }
      }
  }

  //rpc active file
  rpc active-file {
    description 
      "active file";
      input {
        leaf file-name {
          type string;
          description
            "file name";
        }
        leaf file-type {
          type file-type;
          description
            "file type";
        }
      }
      output {
        leaf result {
          type rpc-result;
          description 
            "Result of upload file";
        }
        leaf msg {
          type string;
          description
            "fail reason";
        }
      }
  }
 
  //rpc get active status
  rpc get-active-status {
    description 
      "get active status";
      input {
        leaf file-type {
          type file-type;
          description 
            "file type";
        }
      }
      output {
        leaf result {
          type enumeration {
            enum success {
              value 0;
            }
            enum fail {
              value 1;
            }
            enum processing {
              value 2;
            }
          }   
          description 
            "Result of upload file";
        }
        leaf msg {
          type string;
          description
            "fail reason";
        }
        leaf file-name {
          type string;
          description
            "file name";
        }
        leaf active-time {
          type yang:date-and-time;
          description
            "last active time";
        }
      }
  }

//rpc get download status
  rpc get-download-status {
    description 
      "get download status";
      input {
        leaf file-type {
          type file-type;
          description 
            "file type";
        }
        leaf file-name {
          type string;
          description
            "file name";
        }
      }
      output {
        leaf result {
          type enumeration {
            enum success {
              value 0;
            }
            enum fail {
              value 1;
            }
            enum processing {
              value 2;
            }
          }  
        }
        leaf msg {
          type download-msg-type;
        }
        leaf text{
          type string;
          description
            "detail message form download status";
        }
      }
  }
  
//rpc reset counter
  rpc reset-counter {
    description 
      "clear reset counter";  
      input {
        leaf object-name {
            type string {
                length "1..64";
            }
            mandatory true;
            description "object-name";
        }
        leaf object-type {
            mandatory true;        
            type oc-types:object-type;
             description "object-type";
        }
        leaf pm-parameter-name {       
            type mo-performance-types:pm-parameter-type;
            mandatory true;
            description "pm-parameter-name";
        }
      }
      output {
        leaf result {
          type rpc-result;
          description 
            "Result of reset counter";
        }
      }
  }
        

  //rpc get ne info
  rpc get-ne-info {
    description
      "get ne info";
      output {
        leaf ne-type {
          type string;
          description
            "ne type";
        }
        leaf vendor {
          type string;
          description
            "vendor";
        }
        leaf chassis-type {
          type oc-platform-types:component-chassis-type;
          description
            "chassis type";
        }
       
        leaf result {
          type rpc-result;
          description 
            "Result of reset counter";
        }
        leaf msg {
          type string;
          description
            "fail reason";
        }
      }
  }
        
   rpc switch-mcu {
       description
          "Manual switch the MCU to the standby card";
         input {

           leaf switch-target {
             type leafref {
               path "/oc-platform:components/oc-platform:component/" +
                "oc-platform:name";
             }
             description
               "manual switch the MCU to target card";
           }
         }

         output {
           leaf result {
             type rpc-result;
             description
               "Result of the switch mcu operation";
           }
   		leaf msg {
   		  type string;
   		  description
   		    "fail reason or success msg";
   		}
         }
     }

     rpc get-history-alarms {
       description "get-history-alarms";
       input {
           leaf start-time {
               type yang:date-and-time;
               description "start time for alarm event";
           }
           leaf end-time {
               type yang:date-and-time;
               description "end time for alarm event";
           }
       }
       output {
           container alarms {
               uses mo-alarms:alarms-top;
               description "output alarms";
           }
           container tcas {
               uses mo-tcas:tcas-top;
               description "output tcas";
           }
       }
   }
 
  // notification statements

}
