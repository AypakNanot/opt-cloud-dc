module acc-devm {
    yang-version 1.1;
    namespace "urn:ccsa:yang:acc-devm";
    prefix acc-devm;

    import ietf-yang-types {
        prefix yang;
    }

    import acc-yang-types {
        prefix acc-type;
    }

    import ietf-inet-types {
        prefix inet;
    }
	revision 2024-07-02 {
        description "M-OTN2.0 管控与设备双向调优，减负";
    }
    revision 2021-02-01 {
        description "M-OTN 1.0";
    }
    /*
    * common types
    */
    typedef operational-state {
        type enumeration {
            enum up {
                value 0;
            }
            enum down {
                value 1;
            }
        }
    }
    typedef admin-state {
        type enumeration {
            enum enabled {
                value 0;
            }
            enum disabled {
                value 1;
            }
        }
    }
    typedef laser-status {
        type enumeration {
            enum laser-on {
                value 0;
            }
            enum laser-off {
                value 1;
            }
            enum no-optical-module {
                value 2;
                description "没有光模块";
            }
        }
    }

    typedef loopback-type {
        type enumeration {
            enum facility-loopback {
                value 0;
                description "外环回";
            }
            enum terminal-loopback {
                value 1;
                description "内环回";
            }    
            enum non-loopback {
                value 2;
                description "无环回";
            }
        }
    }

    typedef interface-type {
        type enumeration {
            enum UNI {
                value 0;
                description "客户侧";
            }
            enum NNI {
                value 1;
                description "线路侧";
            }
        }
    }
    typedef service-type {
        type enumeration {
            enum ODU {
                value 0;
            }
            enum SDH {
                value 1;
            }
            enum EPL {
                value 2;
            }
            enum EVPL {
                value 3;
            }
            enum OSU {
                value 4;
            }	
            enum ELAN {
                value 5;
            }
            enum ETREE {
                value 6;
            }
            enum EEPL {
                value 7;
            }
            enum EEVPL {
                value 8;
            }
        }
    }
    typedef me-status {
        type enumeration {
            enum installing {
                value 0;
            }
            enum running {
                value 1;
            }
            enum maintenance  {
                value 2;
            }
        }
    }

    typedef ntp-state {
        type enumeration {
            enum NSET {
                value 0;
            }
            enum FSET {
                value 1;
            }
            enum SPIK {
                value 2;
            }
            enum FREQ {
                value 3;
            }
            enum SYNC {
                value 4;
            }
        }
        description "rfc 5905：clock-never-set，freq-set-from-file，spike-detected，frequency-mode，clock-synchronized";
    }
    typedef reset-type {
        type enumeration {
            enum soft-reset {
                value 0;
            }
            enum hard-reset {
                value 1;
            }
        }
        description "soft-reset doesn't affect service";
    }
    typedef device-type {
        type enumeration {
            enum otm-box {
                value 0;
		description "此类型仅保留，不会被采用了";
            }
            enum po-box {
                value 1;
		description "分组增强型BOX，后续过渡到mo-box";
            }
            enum otm-pnp {
                value 2;
		description "此类型仅保留，不会被采用了";
            }
            enum po-pnp {
                value 3;
		description "分组增强型PNP，后续过渡到mo-pnp";
            }
	    enum mo-box {
                value 4;
		description "固定盒式M-OTN设备";
            }
	    enum mo-pnp {
                value 5;
		description "插板式M-OTN设备";
            }
        }
    }

    typedef port-role {
        type enumeration {
            enum symmetric {
                value 0;
            }
            enum root {
                value 1;
            }
            enum leaf-node {
                value 2;
            }
        }
    }

    typedef protect-role {
        type enumeration {
            enum null {
                value 0;
            }
            enum protected {
                value 1;
            }
            enum primary {
                value 2;
            }
            enum secondary {
                value 3;
            }
        }
    }

    typedef eq-type {
    	type enumeration {
		enum power {
			value 0;
		}
		enum fan {
			value 1;
		}
		enum service {
			value 2;
		}
		enum system-control {
			value 3;
		}
        enum cross-connect {
            value 4;
        }
		enum clock {
			value 5;
		}
        enum eos2eoosu {
            value 6;
            description "Eos2EoOSU桥接板";
        }
        enum extra {
            value 7;
            description "新增的扩展卡";
        }
        enum dispatch {
            value 8;
            description "新增的调度卡";
        }
        enum ose {
            value 9;
            description "新增的管理口业务卡";
        }
	}
    }

    typedef working-state {
        type enumeration {
            enum normal {
                value 0;

            }
            enum backup {
                value 1;
            }
        }
    }
    
    typedef link-direction {
        type enumeration {
            enum uplink {
                value 0;
		description "上联";
            }
            enum downlink {
                value 1;
		description "下联";
            }
        }
    }

    typedef model-type {
         type enumeration {
            enum M1-1 {
                value 0;
		description "固定盒式 模型1";
            }
            enum M1-2 {
                value 1;
		description "固定盒式 模型2";
            }
            enum M1-3 {
                value 2;
		description "固定盒式 模型3";
            }
            enum M1-4 {
                value 3;
		description "固定盒式 模型4";
            }
            enum M1-5 {
                value 4;
		description "固定盒式 模型5";
            }
            enum M2-1 {
                value 5;
		description "插卡 模型1";
            }
            enum M2-2 {
                value 6;
		description "插卡 模型2";
            }
        }
    }
		
    /*
    * groupings
    */
    grouping state-pac {
        leaf operational-state {
            mandatory true;
            type operational-state;
            config false;
        }
        leaf admin-state {
            mandatory true;
            type admin-state;
        }
    }

    grouping ftp {
        leaf name {
	        mandatory true;
            type string{
            length "1..64";
            }
        }
    	leaf eq {
    	    type string;
            mandatory true;
    	    description "parent EQ";
    	}
        container state-pac {
            uses state-pac;
        }
        leaf layer-protocol-name {
            mandatory true;
            type identityref {
                base acc-type:layer-protocol-name;
            }
        }
        leaf-list client-ctp {
            type leafref {
                path '/acc-devm:ctps/acc-devm:ctp/acc-devm:name';
            }
        }
        leaf-list server-ctp {
            type leafref {
                path '/acc-devm:ctps/acc-devm:ctp/acc-devm:name';
            }
        }
    }

    grouping ctp {
        leaf name {
	        mandatory true;
            type string{
            length "1..64";
            }
            description "Name of ctp";
        }
        container state-pac {
            uses state-pac;
            description "State of ctp";
        }
        leaf layer-protocol-name {
            mandatory true;
            type identityref {
                base acc-type:layer-protocol-name;
            }
        }
        leaf port-role {
            type port-role;
            default "symmetric";
            config false;
            description "default value symmetric";
        }
        leaf protect-role {
            mandatory true;
            type protect-role;
            config false;
        }
        leaf server-tp {
            type string;
            description "父端口的名字，eos和eoosu模型里的eth ftp绑定的eth-ftp-vc-ctp是没有server-tp的，这个比较特殊。";
        }

	leaf client-tp {
            type string{
            length "1..64";
            }
            description "例如eos场景下eth-ftp绑定的那个vc ctp，其client-tp为关联的那个eth-ftp";
        }
        leaf loop-back {
            default "non-loopback";
            type loopback-type;
            description "Loop back type of ctp,default non-loopback";
        }
    }

    grouping mc-port {
        leaf name {
            mandatory true;
            type string;
            description "命名规则：端口类型加序号，如：RJ45_1, USB_1, Serial_1";
        }
        leaf mac-address {
            type string;
            config false;
        }
        leaf operational-state {
            mandatory true;
            type operational-state;
            config false;
        }
        leaf admin-state {
            mandatory true;
            type admin-state;
        }
    }

    grouping ftr {
        leaf uuid {
	        mandatory true;
            type string;
            description "真正设备唯一标识，无论断电重启等任何条件都始终保证不变，建议以管理口mac地址或者串号作为标识";
        }
        leaf name {
	        mandatory true;
            type string{
              length "1..64";
            }
        }
        leaf serial-number {
	        mandatory true;
            type string;
            config false;
            description "设备序列号或串号，省公司需求，如果uuid已经采用了序列号或者串号，这里重复填写一遍";
        }
        leaf manufacturer {
            mandatory true;
            type string{
              length "1..32";
            }
            config false;
            description "Manufacturer";
        }
        leaf product-name {
            mandatory true;
            type string{
              length "1..32";
            }
            config false;
            description "Product name";
        }
        leaf software-version {
            mandatory true;
            type string{
              length "1..32";
            }
            config false;
            description "Software version";
        }
        leaf hardware-version {
            mandatory true;
            type string{
              length "1..32";
            }
            config false;
            description "Hardware version";
        }
        leaf device-type {
            mandatory true;
            type device-type;
            config false;
            description "mo-box";
        }
        leaf model-type {
            type model-type;
            config false;
            description "模型几";
        }

    }
    /*
    * the data tree
    */
    container me {
        leaf name {
	        mandatory true;
            type string{
              length "1..64";
            }
            description "for UMS, it's a label";
        }
        leaf uuid {
	        mandatory true;
            type string;
            config false;
            description "真正设备唯一标识，无论断电重启等任何条件都始终保证不变，建议以管理口mac地址或者串号作为标识";
        }
        leaf serial-number {
            mandatory true;
            type string;
            config false;
            description "设备序列号或串号，省公司需求，如果uuid已经采用了序列号或者串号，这里重复填写一遍";
        }
        leaf status {
            mandatory true;
            type me-status;
        }
        leaf manufacturer {
            mandatory true;
            type string{
              length "1..32";
            }
            config false;
            description "Manufacturer";
        }
        leaf product-name {
            mandatory true;
            type string{
              length "1..32";
            }
            config false;
            description "Product name";
        }
        leaf software-version {
            mandatory true;
            type string{
              length "1..32";
            }
            config false;
            description "Software version";
        }
        leaf hardware-version {
            mandatory true;
            type string{
              length "1..32";
            }
            config false;
            description "Hardware version";
        }
        leaf device-type {
            mandatory true;
            type device-type;
            config false;
            description "Device type";
        }
        leaf model-type {
            type model-type;
            config false;
            description "模型几";
        }
        leaf-list layer-protocol-name {
            type identityref {
                base acc-type:layer-protocol-name;
            }
            min-elements 1;
            config false;
            description "Layer protocol name";
        }
        leaf ip-address {
            mandatory true;
            type inet:ipv4-address;
            description "Ip address(ipv4)";
        }
        leaf mask {
            mandatory true;
            type yang:dotted-quad;
            description "Mask";
        }
        leaf ntp-enable {
            default false;
            type boolean;
            description "Support ntp or not.";
        }
        leaf ntp-state {
            default "NSET";
            type ntp-state;
            config false;
            description "ntpState提到这里，当ntpEnable使能后,代表网元与ntpServer同步的最终结果";
        }
        leaf ntp-server-in-use {
            type string {
                length "1..32";
            }
            config false;
            description "ntpServer name";
        }
        container ntp-servers {
            list ntp-server {
                key 'name';
                leaf name {
                    type string {
                        length "1..32";
                    }
                    description "Name of ntp server.";
                }
                leaf ip-address {
                    mandatory true;
                    type inet:ipv4-address;
                    description "Ip address of ntp";
                }
                leaf port {
                    type inet:port-number;
                    default 123;
                    description "Port number of ntp";
                }
                leaf ntp-version {
                    type string {
                        length "1..64";
                    }
                    default "V3";
                    description "Ntp version default value: V3";
                }

            }
        }
        leaf gate-way1 {
            mandatory true;
            type inet:ipv4-address;
            description "Gat way1(ipv4)";
        }
        leaf gate-way2 {
            type inet:ipv4-address;
            description "Gat way2(ipv4)";
        }
        leaf-list eq {
            type leafref {
                path '/acc-devm:eqs/acc-devm:eq/acc-devm:name';
            }
            min-elements 1;
            config false;
            description "Eq list";
        }
        leaf-list mc-port {
            type leafref {
                path '/acc-devm:mc-ports/acc-devm:mc-port/acc-devm:name';
            }
            min-elements 1;
            config false;
        }
    	leaf total-slot-number {
    	    mandatory true;
    	    type uint16;
    	    description "设备所有槽位的数量，用于面板图绘制";
    	}
        leaf yang-version {
            type string;
            description "Yang的版本，未升级设备默认不报此参数，管控系统视为旧模型，24年发布的支持AlarmMaskConfigData功能的为新模型，必须上报，固定按YANG 在线地址提供的版本号上报，即 “2.5.1”";
        }
	
    }
    grouping ptps-grouping {
        list ptp {
            key 'name';
            min-elements 1;
            leaf name {
                type string{
                length "1..64";
                }
                description "Name of ptp, unique";
            }
	    leaf eq {
	        mandatory true;
	    	type string;
		description "parent EQ";
	    }
	    leaf direction {
	       type link-direction;
	       description "暂时用不上。定义上下联的方向，便于后续串接时辨识端口位置，对于CPE来讲，线路侧为上联，客户侧为下联方向；对于插板，与CPE相连的方向为下联，与大网连接的方向为上联";
	    }
        leaf panel-name {
	       type string;
           config false;
	       description "设备物理面板上标记的端口名，如C1，L1，或纯数字，要求与设备面板标记必须相同";
	    }
        leaf ems-name {
	       type string;
           config false;
	       description "厂商自己的EMS网管上显示的该端口的全称";
	    }
            container state-pac {
                uses state-pac;
                description "State of ptp";
            }
            leaf layer-protocol-name {
                mandatory true;
                type identityref {
                base acc-type:layer-protocol-name;
            }
                description "current protocol setting value";
            }
            leaf-list supported-layer-protocol-name {
                config false;
                type identityref {
                    base acc-type:layer-protocol-name;
            }
                description "all supported abilities of protocol";
            }
            leaf peer-ip-address {
                type inet:ipv4-address;
		default "0.0.0.0";
                config false;
                description "对端ip，若没有连纤，使用默认值0.0.0.0";
            }
            leaf peer-tcp-id {
                type string {
                    length 8;
		    pattern "[0-9a-f]{8}";
                }
                config false;
		default "00000000";
                description "对端端口，若没有连纤，使用默认值00000000";
            }
            leaf local-tcp-id {
	    	mandatory true;
                type string {
                    length 8;
		    pattern "[0-9a-f]{8}";
                }
                config false;
                description "本端端口，必须与当前端口信息一致";
            }
            leaf laser-status {
                type laser-status;
                description "虽然企标定义可选，但建议电口的PTP也上报为 no-optical-module,其他光口必须上报";
            }
            leaf-list ctp {
                type leafref {
                    path '/acc-devm:ctps/acc-devm:ctp/acc-devm:name';
                }
                description "Ctp list";
            }
            leaf interface-type {
                mandatory true;
                type interface-type;
                description "Interface type of ptp";
            }
            leaf loop-back {
                default "non-loopback";
                type loopback-type;
                description "default non-loopback";
            }
            leaf-list remote-ptp {
                 type leafref {
                    path '/acc-devm:ptps/acc-devm:ptp/acc-devm:name';
                 }
                 config false;
                 description "按企标上此参数已经是leaf类型了，在此咱不修改了，规定一下只能上报一个与当前端口连接的光猫端口，不允许报多个";
            }
            leaf-list FTR {
                type string;
                description "如果当前PTP是光猫的PTP，则必须上报所属光猫的uuid，其它正常端口不上报此属性";
            }
            container optical-power-pac {
                description "如果激光器为打开状态，必须上报";
                leaf input-power {
                    mandatory true;
                    type acc-type:real;
                    config false;
                    description "Input power of ptp";
                }
                leaf output-power {
                    mandatory true;
                    type acc-type:real;
                    config false;
                    description "Output power of ptp";
                }
                leaf input-power-upper-threshold {
                    mandatory true;
                    type acc-type:real;
                    config false;
                    description "Input power upper threshold of ptp";
                }
                leaf input-power-lower-threshold {
                    mandatory true;
                    type acc-type:real;
                    config false;
                    description "Input power lower threshold of ptp";
                }
                leaf output-power-upper-threshold {
                    mandatory true;
                    type acc-type:real;
                    config false;
                    description "Output power upper threshold of ptp";
                }
                leaf output-power-lower-threshold {
                    mandatory true;
                    type acc-type:real;
                    config false;
                    description "Output power lower threshold of ptp";
                }            
            }
        }
    }

    container ptps {
        uses ptps-grouping;
    }

    container specifc-ptps {
        uses ptps-grouping;
    }

    container ftps {
        list ftp {
            key 'name';
            uses ftp;
        }
    }    
    container ctps {
        list ctp {
            key 'name';
            uses ctp;
        }
    } 
    container ftrs {
        list ftr {
            key 'uuid';
            uses ftr;
        }
    }    
    container mc-ports {
        list mc-port {
            key 'name';
            uses mc-port;
        }
    }
    container eqs {
        list eq {
            key 'name';
            min-elements 1;
            leaf name {
                type string {
                    length "1..64";
                }
            }
	    leaf model {
                  mandatory true;
		  type string;
		  description "必须与集采时上报的型号一致，区分大小写";
	    }
            leaf serial-number {
	        mandatory true;
                type string;
                config false;
                description "板卡的序列号或串号，省公司需求";
	    }
            leaf plug-state {
                mandatory true;
                type boolean;
                config false;
            }
    	    leaf-list eq-type {
    		      config false;
    		      type eq-type;
                  min-elements 1;
    	    }
	    leaf xc-capability {
	        default true;
	        type boolean;
	    }
	    leaf working-state {
	       type working-state;
               default "normal";
	    }
            leaf software-version {
                type string{
                    length "1..32";
                }
                config false;
            }
            leaf hardware-version {
                type string{
                    length "1..32";
                }
                config false;
            }
            leaf-list ptp {
                min-elements 0;
                type leafref {
                    path '/acc-devm:ptps/acc-devm:ptp/acc-devm:name';
                }
                config false;
                description "仅保留此字段，后续不使用此值，因在ptp中已标识父EQ";
            }
            leaf-list ftp {
                min-elements 0;
                type leafref {
                    path '/acc-devm:ftps/acc-devm:ftp/acc-devm:name';
                }
                config false;
                description "仅保留此字段，后续不使用此值，因在ftp中已标识父EQ";
            }
            leaf osu-bandwidth {
                type uint16;
                description "仅针对osu，板卡所支持的OSU总带宽";
            }
            leaf osu-number {
                type uint16;
                description "仅针对osu，板卡所支持的OSU总连接数";
            }
            leaf desp{
                type string;
                description "如果此卡未在eqType枚举内，类型特殊，需要额外在此做简单说明卡的作用、能力等，eqType使用extra";
            }
            leaf low-power-indentifier {
                type boolean;
                description "是否支持低功耗能力";
            } 
            leaf low-power-state {
                type string;
                description "单板低功耗使能状态：ENABLED（低功耗使能），DISABLED（低功耗禁止）";
            } 
        }
    }

 
    notification peer-change-notification {
        leaf ptp-name {
            mandatory true;
            type string {
                length 1..64;
            }
        }
        leaf peer-ip-address {
              mandatory true;
              type inet:ipv4-address;
        }
        leaf peer-ptp-tcp-id {
              mandatory true;
            type string {
                length 8;
		pattern "[0-9a-f]{8}";
            }
        }
    } 

    notification ftr-change-notification {
        leaf ptp-name {
            mandatory true;
            type string {
                length 1..64;
            }
        }
        leaf remote-ptp {
              mandatory true;
              type string;
	      description "当插拔PTP探测到FTR端口连接后，必须填写；如果探测到拔出，则更新为空字符串";
        }
        leaf model-type {
            type model-type;
            description "默认普通，不用报。 当为智能光猫且是代管方式的时候才需上报， 直管方式采用正常固定盒式上线消息。 ";
        }
        leaf FTR {
              mandatory true;
              type string;
	      description "FTR的uuid，当插拔PTP探测到FTR端口连接后，必须填写；如果探测到拔出，则更新为空字符串";
        }
    } 
    
    /*
    * RPCs
    */
    rpc reset {
        input {
            leaf eq-name {
                mandatory true;
                type string{
                  length "1..64";
                }
            }
            leaf reset-type {
                mandatory true;
                type reset-type;
            }
        }
    }

    rpc modify-user-password {
        input {
            leaf user-name {
                type string;
		description "可选，默认当前用户";
            }
            leaf old-password {
                mandatory true;
                type string {
                    length "8..16";
                }
            }
            leaf new-password {
                mandatory true;
                type string {
                    length "8..16";
                }
            }
        }
    }
    
    rpc set-managed-element-time {
        input {
            leaf new-time {
                mandatory true;
                type yang:date-and-time;
                }
         }
    }
	
    rpc get-managed-element-time {
        output {
            leaf date-time {
                mandatory true;
                type yang:date-and-time;
                }
        }
    }

    grouping optical-module-info {
        leaf ptp-name {
            mandatory true;
            type string;
        }
        leaf vendor {
            mandatory true;
            type string;
            description "厂商";
        }
        leaf sn {
            mandatory true;
            type string;
            description "序列号";
        }
        leaf pn {
            mandatory true;
            type string;
            description "类型/型号";
        }
        leaf ver {
            mandatory true;
            type string;
            description "版本号";
        }
        leaf temperature {
            mandatory true;
            type string;
            description "温度 默认单位摄氏度";
        }
        leaf input-pow {
            mandatory true;
            type string;
            description "输入光功率";
        }
        leaf output-pow {
            mandatory true;
            type string;
            description "输出光功率 ";
        }
        leaf voltage {
            type string;
            description "电压 默认单位伏特";
        }
        leaf cur {
            type string;
            description "偏流/电流 默认单位毫安";
        }

        leaf packaging-mode {
            type string;
            description "光模块封装模式 枚举值： SFP,SFP+,CSFP,CXP,CXP2,GBIC";
        }
        leaf wave-length {
            type string;
            description "收发波长 默认单位nm  枚举：850，1310，1550";
        }
        leaf receive-character {
            type string;
            description "收发特性 单纤双向(单纤）和 单纤单向(双纤）枚举：BIDI，UNIDI， 不支持默认按UNIDI报";
        }
        leaf fiber-mode {
            type string;
            description "光纤模式  单模光纤： SMF ，多模：MMF 不支持默认按SMF报";
        }
        leaf sensitivity {
            type string;
            description "灵敏度, 单位dBm  不支持默认报空值";
        }
        leaf overload-point {
            type string;
            description "过载点, 单位dBm  不支持默认报空值";
        }
        leaf tuned-frequency {
            type string;
            description "频率,单位THZ  不支持默认报NS";
        }
        leaf additional {
            type string;
            description "若有其它特有的光模块信息，可在这里补充，没有固定形式，表述清楚即可";
        }
        description "全部类型为string，即不强行统一单位，各参数厂商根据实际光模块的信息补充单位，能描述清楚即可";
    }

    rpc get-optical-module-info {
        input {
            leaf ptp-name {
                type string;
                description "可选，若指定则只返回单个信息，若不传或者空值则返回所有光模块信息";
            }
        }
        output {
            container optical-module-infos {
                list optical-module-info {
                    key 'ptp-name';
                    uses optical-module-info;
                    description 'optical-module-info list';
                }
                description 'optical-module-info container';
            }
        }
    }

    rpc get-eq-temperature{
        input{
            leaf eq-name {
                type string;
                description "可选，若指定则只返回单个单板，若不传或者空值则返回所有单板温度";
            }
        }
        output{
           container eq-temperatures{
                list eq-temperature{
                    key 'eq-name';
                    leaf eq-name {
                        type string;
                    }
                    leaf temperature{
                        type string;
                        description "默认单位摄氏度，如果获取全量单板的温度，为精简报文，只返回有温感器单板的数据；若查询指定的单板无温感器，直接报错信息提示 no-sensor";
                    }
                    
                }
           }           
        }
    }

    rpc set-board-sleep-mode {
        description "单板低功耗设置";
        input {
            leaf eq-name {
                mandatory true;
                type string{
                  length "1..64";
                }
            }
            leaf low-power-state {
                mandatory true;
                type string;
            }
        }
    }
}
