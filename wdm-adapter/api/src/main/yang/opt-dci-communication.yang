module opt-dci-communication {
    yang-version 1;
    namespace "com:optel:device:opt:dci:communication";
    prefix "opt-dci-communication";

    revision "2022-09-28" {
        description "DCI communication";
    }

    import base-types  {prefix "base-types";}
    import optel-oc-nat {prefix "oc-nat";}
	rpc get-nat {
		input {
    		uses base-types:ne-common-prop;
		}
		output {
		    uses oc-nat:nats-top;
		}
	}

	rpc set-nat {
		input {
			uses base-types:ne-common-prop;
			uses oc-nat:nat-config;
		}
	}

    rpc delete-nat {
		input {
    		uses base-types:ne-common-prop;
    		leaf index{
    		   type uint32;
    		}
		}
	}

}
