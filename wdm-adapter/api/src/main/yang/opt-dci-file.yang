module opt-dci-file {
    yang-version 1;
    namespace "com:optel:device:opt:dci:file";
    prefix "opt-dci-file";

    revision "2020-02-10" {
        description "DCI DEVICE";
    }

    import base-types  {prefix "base-types";}
    import optel-oc-rpc {prefix "opt-oc-rpc";}
    import ietf-yang-types { prefix yang; }

    rpc download-file-ne {
        description
              "download file";
         input {
            uses base-types:ne-common-prop;
            leaf file-type {
              type opt-oc-rpc:file-type;
              description
                "file-type";
            }
            leaf file-name {
              type string;
              description
                "file name";
            }
            leaf path {
              type string;
              description
                "[sftp]://hostname/directorypath/filename";
            }
            leaf username {
              type string;
              description
                "username";
            }
            leaf password {
              type string;
              description
                "password";
            }
          }
          output {

            leaf msg {
                type string;
            // type opt-oc-rpc:download-msg-type;
              description
                "fail reason";
            }
          }
    }

    rpc upload-file-ne{
        description
          "upload file";
          input {
            uses base-types:ne-common-prop;
            leaf path {
              type string;
              description
                "path";
            }
            leaf file-type {
              type enumeration {
                enum data {
                  value 0;
                }
                enum log {
                  value 1;
                }
              }
            }
            leaf file-name {
              type string;
              description
                "file name";
            }
            leaf username {
              type string;
              description
                "username";
            }
            leaf password {
              type string;
              description
                "password";
            }
          }
          output {

            leaf msg {
              type string;
              //type opt-oc-rpc:upload-msg-type;
              description
                "fail reason";
            }
            leaf md5 {
              type string;
              description
                "md5";
            }
            leaf file-name {
              type string;
              description
                "real file-name";
            }
          }
    }

    rpc get-file-list-ne{
        input {
          uses base-types:ne-common-prop;
          leaf file-type {
            type enumeration {
              enum data {
                value 0;
              }
              enum upgrade {
                value 1;
              }
              enum log {
                value 2;
              }
              enum all {
                value 3;
                description
                  "all file type";
              }
            }
          }
        }
        output {
          leaf msg {
            type string;
          }
          list file-names {
            key 'file-name';
            leaf file-name {
              type string;
            }
          }
        }
    }

    rpc active-file-ne {
        description
        "active file";
	  input {
	    uses base-types:ne-common-prop;
	    leaf file-name {
		  type string;
		  description
		    "file name";
		}
		leaf file-type {
		  type opt-oc-rpc:file-type;
		  description
		    "file type";
		}
	  }
	  output {

		leaf msg {
		  type string;
		  description
		    "fail reason";
		}
	  }
    }

    rpc get-active-status-ne{
        description
          "get active status";
          input {
            uses base-types:ne-common-prop;
            leaf file-type {
              type opt-oc-rpc:file-type;
              description
                "file type";
            }
          }
          output {
            leaf result {
              type enumeration {
                enum success {
                  value 0;
                }
                enum fail {
                  value 1;
                }
                enum processing {
                  value 2;
                }
              }
              description
                "Result of upload file";
            }
            leaf msg {
              type string;
              description
                "fail reason";
            }
            leaf file-name {
              type string;
              description
                "file name";
            }
            leaf active-time {
              type yang:date-and-time;
              description
                "last active time";
            }
          }
    }

    rpc get-download-status-ne{
        description
          "get download status";
          input {
            uses base-types:ne-common-prop;
            leaf file-type {
              type opt-oc-rpc:file-type;
              description
                "file type";
            }
            leaf file-name {
              type string;
              description
                "file name";
            }
          }
          output {
            leaf result {
              type enumeration {
                enum success {
                  value 0;
                }
                enum fail {
                  value 1;
                }
                enum processing {
                  value 2;
                }
              }
            }
            leaf msg {
               type string;
              //type opt-oc-rpc:download-msg-type;
            }
          }
    }

}
