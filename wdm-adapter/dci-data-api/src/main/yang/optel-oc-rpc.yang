module optel-oc-rpc {

  yang-version "1";

    // namespace
  namespace "com:optel:dci:yang://rpc";

  prefix "oc-rpc";

  // import 
  import optel-oc-types { prefix oc-types; }
  import optel-oc-yang-types { prefix oc-yang; }
  import optel-oc-transport-types { prefix oc-opt-types; }
  import ietf-yang-types { prefix yang; }
  import optel-oc-performance-types { prefix oc-performance-types; }
  import optel-oc-inet-types { prefix oc-inet; }
  import optel-oc-platform-types { prefix oc-platform-types; }


  // meta
  organization "private";

  description
    "This YANG module contains all RPCs for OLS systems.
       This module includes all RPCs usable by NETCONF.";

  revision "2022-02-08" {
    description
      "Initial release version";
    reference "0.1.0";
  }

  // typedef statements
  
  typedef file-type {
    type enumeration {
	  enum data {
	    description "data";
	  }
	  enum upgrade {
		description "upgrade";
	  }
	}
  }
  
  typedef download-msg-type {
    type enumeration {
	  enum 0-success {
	    description
		  "success";
	  }
	  enum 100-socket-fail {
	    description
		  "socket-fail";
	  }
	  enum 110-auth-fail {
	    description
		  "auth-fail";
	  }
	  enum 120-file-not-exist {
	    description
		  "file-not-exist";
	  }
	  enum 130-timeout {
	    description
		  "timeout";
	  }
	  enum 140-validate-fail {
	    description
		  "validate-fail";
	  }
	  enum 150-file-type-mismatch {
	    description
		  "file-type-mismatch";
	  }
	  enum 999-custom {
	    description
		  "custom";
	  }
	}
  }
  
  typedef upload-msg-type {
    type enumeration {
	  enum 0-success {
	    description
		  "success";
	  }
	  enum 100-socket-fail {
	    description
		  "socket-fail";
	  }
	  enum 110-auth-fail {
	    description
		  "auth-fail";
	  }
	  enum 130-timeout {
	    description
		  "timeout";
	  }
	  enum 150-file-type-mismatch {
	    description
		  "file-type-mismatch";
	  }
	  enum 999-custom {
	    description
		  "custom";
	  }
	}
  }

  // grouping statements 

  // rpc statements
      grouping reboot-input-grouping {
        leaf component-name {
          type string;
          description
             "target reboot components";
        }       

        leaf reboot-type {
          type enumeration {
            enum warm { 
              description "warm reboot";
            }
            enum cold { 
              description "cold reboot";
            }
          }
          description 
            "Reboot type";
        }
      }


   
  //rpc switch olp
      grouping switch-olp-input-grouping {
        
        leaf name {
          type string;
          description
             "target aps name";
        }  
      
        leaf switch-to-port {
          type enumeration {
            enum PRIMARY {
              description
                "manual switch the OLP to the primary line port";
            }
            enum SECONDARY {
              description
                "manual switch the OLP to the secondary line port";
            }
          }
          description
            "manual set the optical switch to a port";
        }
      }
  

    // rpc set-datetime
      grouping set-datetime-input-grouping {
        leaf datetime {
          type yang:date-and-time;
          description
             "Target datetime to be set";
        }       
      }
  
  //rpc get oduk delay
      grouping get-oduk-delay-input-grouping {
        leaf index {
          type uint32;
          description
             "The index of logical channel(ODU)";
        }  

		leaf delay-test-times {
          type uint32;
          description
             "Measurement repeated times.";
        }  
      }

      grouping get-oduk-delay-output-grouping {
		container delay-data-value {
          uses oc-opt-types:avg-min-max-instant-stats-precision2-ns;
          description
             "Test results of ODUk delay measurement";
        }  	
      }

  //rpc download file
	  grouping download-file-input-grouping {
	    leaf file-type {
		  type file-type; 
		  description 
		    "file-type";
	    }
		leaf file-name {
		  type string;
		  description
		    "file name";
		}
		leaf path {
		  type string;
		  description
		    "[sftp]://hostname/directorypath/filename";
		}
		leaf username {
		  type string;
		  description
		    "username";
		}	
	    leaf password {
		  type string;
		  description
		    "password";
		}	
	  }


  //rpc upload file
	  grouping upload-file-input-grouping {
	    leaf path {
		  type string;
		  description
		    "path";
		}
	    leaf file-type {
		  type enumeration {
		    enum data {
			  value 0;
			}
			enum log {
			  value 1;
			}
		  }
	    }
		leaf file-name {
		  type string;
		  description
		    "file name";
		}
		leaf username {
		  type string;
		  description
		    "username";
		}	
	    leaf password {
		  type string;
		  description
		    "password";
		}	
	  }
	  grouping upload-file-output-grouping {
		leaf md5 {
		  type string;
		  description
		    "md5";
		}
		leaf file-name {
		  type string;
		  description
		    "real file-name";
		}
	  }
  
  //rpc get-file-list
    grouping get-file-list-input-grouping {
	  leaf file-type {
	    type enumeration {
		  enum data {
		    value 0;
		  }
		  enum upgrade {
		    value 1;
		  }
		  enum log {
		    value 2;
		  }
		  enum all {
		    value 3;
		    description 
			  "all file type";
		  }
		}
	  }
	}
	grouping get-file-list-output-grouping {
      list file-names {
        key 'file-name';
        leaf file-name {
          type string;
        }
	  }  
	}
  
  //rpc delete file
	  grouping delete-file-input-grouping {
	    leaf file-name {
		  type string;
		  description
		    "file name";
		}
		leaf file-type {
		  type file-type;
		  description
		    "file type";
		}
	  }


  //rpc active file
	  grouping active-file-input-grouping {
	    leaf file-name {
		  type string;
		  description
		    "file name";
		}
		leaf file-type {
		  type file-type;
		  description
		    "file type";
		}
	  }

 
  //rpc get active status
	  grouping get-active-status-input-grouping {
	    leaf file-type {
		  type file-type;
		  description 
		    "file type";
	    }
	  }
	  grouping get-active-status-output-grouping {
	    leaf result {
		  type enumeration {
		    enum success {
			  value 0;
			}
			enum fail {
			  value 1;
			}
			enum processing {
			  value 2;
			}
		  }   
          description 
            "Result of upload file";
        }
		leaf msg {
		  type string;
		  description
		    "fail reason";
		}
		leaf file-name {
		  type string;
		  description
		    "file name";
		}
		leaf active-time {
		  type yang:date-and-time;
		  description
		    "last active time";
		}
	  }

//rpc get download status
	  grouping get-download-status-input-grouping {
	    leaf file-type {
		  type file-type;
		  description 
		    "file type";
	    }
		leaf file-name {
		  type string;
		  description
		    "file name";
		}
	  }
	  grouping get-download-status-output-grouping {
	    leaf result {
		  type enumeration {
		    enum success {
			  value 0;
			}
			enum fail {
			  value 1;
			}
			enum processing {
			  value 2;
			}
		  }  
        }
        leaf msg {
           type string;
		  //type download-msg-type;
		}
	  }
  
//rpc reset counter
	  grouping reset-counter-input-grouping {
	    leaf pm-point {
          type oc-performance-types:pm-point-ref;
          description
            "The path of the performance monitoring point";
        }
		leaf pm-point-type {
          type oc-performance-types:pmp-object-type;
          description
            "Categories of performance monitoring objects.";
        }
	  }
	
//rpc set neighbour ip
	  grouping set-neighbour-ip-input-grouping {
	    leaf local-port{
          type string;
          description
            "local port of OSC";
        }
        leaf neighbor-id {
          type string;
          description
            "neighbor id";
        }
        leaf neighbor-ip-type {
          type enumeration {
            enum NM {
              value 0;
            }
            enum OSC {
              value 1;
            }
            enum LOOPBACK {
              value 2;
            }
          }
          description
            "neighbor ip type";
        }
        leaf neighbor-ip {
          type oc-inet:ipv4-address;
          description
            "neighbor ip";
        }
        leaf neighbor-port-name {
          type string;
          description
            "neighbor port name";
        }
        leaf neighbor-prefix-length {
          type uint8;
          description
            "subnet mask code length";
        }
        leaf neighbor-gateway {
          type oc-inet:ipv4-address;
          description
            "neighbor gateway";
        }
	  }

	  grouping get-ne-info-output-grouping {
	    leaf ne-type {
		  type string;
		  description
		    "ne type";
		}
		leaf chassis-type {
		  type oc-platform-types:component-chassis-type;
		  description
		    "chassis type";
		}
	    leaf ola {
	      type boolean;
	   	  description 
		    "whether chassis is used as ola ";
		}
      }

      grouping get-ne-common-resource-grouping {
        uses get-ne-info-output-grouping;
        leaf hardware-version {
            type string;
        }
        leaf firmware-version {
            type string;
        }
        leaf software-version {
            type string;
        }
        leaf ntp-enabled {
            type boolean;
        }
        leaf lldp-enabled {
            type boolean;
        }
        leaf description {
            type string;
        }
        leaf mfg-name {
            type string;
        }
        leaf mfg-date {
            type oc-yang:date;
        }
        leaf serial-no {
            type string;
        }
        leaf part-no {
            type string;
        }
        leaf production-num {
          type string;
        }
        leaf admin-state {
            type oc-opt-types:admin-state-type;
        }
        leaf rated-power {
            type uint32;
        }
      }
		  
  // notification statements

}
