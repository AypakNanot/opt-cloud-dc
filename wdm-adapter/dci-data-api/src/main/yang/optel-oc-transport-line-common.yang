module optel-oc-transport-line-common {

  yang-version "1";

  // namespace
  namespace "com:optel:dci:yang://transport-line-common";

  prefix "oc-line-com";

  // import some basic types

  import optel-oc-interfaces { prefix oc-if; }
  import optel-oc-types { prefix oc-types; }
  import optel-oc-transport-types { prefix oc-opt-types; }
  import optel-oc-platform-transceiver { prefix oc-transceiver; }
  import optel-oc-platform-mux { prefix oc-mux; }
  import optel-oc-yang-types { prefix oc-yang; }


  // meta
  organization "OpenConfig working group";

  contact
    "OpenConfig working group
    www.openconfig.net";

  description
    "This module defines common data elements for OpenConfig data
    models for optical transport line system elements, such as
    amplifiers and ROADMs (wavelength routers).";

  revision "2022-02-08" {
    description
      "Initial public release";
    reference "0.1.0";
  }

  // extension statements

  // feature statements

  // identity statements

  // typedef statements

  // grouping statements
  
  grouping optical-osc-statistics{
    description
      "Operational statistics data for OSC interfaces";
	  
    leaf es {
      type decimal64{
        fraction-digits 2;
      }
	  
      description
        "Errored Seconds of the interface, signal rate includes
		 2Mbps, SDN/OTN.";
    }
	
	leaf ses {
      type decimal64{
        fraction-digits 2;
      }
	  
      description
        "Severely Errored Seconds of the interface, signal rate includes
		 2Mbps, SDN/OTN.";
    }
	
	leaf fees {
      type decimal64{
        fraction-digits 2;
      }
	  
      description
        "Far-end Errored Seconds of the interface, signal rate includes
		 2Mbps, SDN/OTN.";
    }
	
	leaf feses {
      type decimal64{
        fraction-digits 2;
      }
	  
      description
        "Far-end Severely Errored Seconds of the interface, signal rate includes
		 2Mbps, SDN/OTN.";
    }
	
	leaf uas {
      type decimal64{
        fraction-digits 2;
      }
	  
      description
        "Unavailable Seconds of the interface, signal rate includes
		 2Mbps, SDN/OTN.";
    }
	
	leaf rx-message-num {
      type uint32;
	  
      description
        "Recieved message numbers of the interface, signal rate includes
		 100BaseFX.";
    }
	
	leaf tx-message-num {
      type uint32;
	  
      description
        "Transmited message numbers of the interface, signal rate includes
		 100BaseFX.";
    }
	
	leaf rx-drop-message-num {
      type uint32;
	  
      description
        "Dropped received message numbers of the interface, signal rate includes
		 100BaseFX.";
    }
  }

   grouping optical-osc-config {
    description
      "Configuration data for OSC interfaces";

    leaf interface-name{
      mandatory true;
      type oc-if:base-interface-ref;
      description
        "Reference to an OSC interface";
    }
  }

  grouping optical-osc-state {
    description
      "Operational state data for OSC interfaces";

    container input-power {
      description
        "The input optical power of this port in units
        of 0.01dBm. If avg/min/max statistics are not supported,
        the target is expected to just supply the instant value";

      uses oc-types:avg-min-max-instant-stats-precision2-dBm;
    }

    container output-power {
      description
        "The output optical power of this port in units
        of 0.01dBm. If avg/min/max statistics are not supported,
        the target is expected to just supply the instant value";

      uses oc-types:avg-min-max-instant-stats-precision2-dBm;
    }

    container laser-bias-current {
      description
        "The current applied by the system to the transmit laser to
        achieve the output power. The current is expressed in mA
        with up to one decimal precision. If avg/min/max statistics
        are not supported, the target is expected to just supply
        the instant value";

      uses oc-types:avg-min-max-instant-stats-precision2-mA;
    }

    uses oc-transceiver:output-optical-frequency;
	
	//statistics
	uses optical-osc-statistics;
  }



  grouping optical-osc-top {
    description
      "Top-level grouping for configuration and operational state
      data for optical supervisory channels (OSC) for amplifiers,
      WSS/ROADM, nodes, etc.";
      uses optical-osc-config;
      uses optical-osc-state;
  }


  grouping transport-line-common-port-config {
    description
      "Configuration data for optical line ports";

    leaf admin-state {
      type oc-opt-types:admin-state-type;
      description
          "Sets the admin state of the optical-port";
    }
    leaf power-offset {
      type decimal64{
        fraction-digits 2;
      }
	  description
	    "only for OCM";
	}
  }

  grouping transport-line-common-port-state {
    description
      "Operational state data describing optical line ports";

    leaf optical-port-type {
      //mandatory true;
      type identityref {
        base oc-opt-types:OPTICAL_PORT_TYPE;
      }
      description
        "For physical ports belonging to optical transport
        devices, this indicates the type of optical port.  This is an
        informational field that should be made available by the
        device.";
    }

    leaf tilt {
      type decimal64 {
        fraction-digits 2;
      }
      units dB;
      description
        "The total tilt measured on the port. This is applicable to
	       ports of type INGRESS and EGRESS.";
    }

	leaf mon-type {
	  type enumeration {
	    enum OTDR {
		  description 
		    "OTDR";
		}
		enum OCM {
		  description 
		    "OCM";
		}
	  }
	  description
	  "Only for OA/OLA MON";
	}
	leaf mon-object {
	  type string;
	  description
	  "Only for OA/OLA MON";
	}
    container input-power {
      description
        "For line system device ports, this value indicates
        the total input optical power of the port in units
        of 0.01dBm. If avg/min/max statistics are not supported,
        just supply the instant value";

      uses oc-types:avg-min-max-instant-stats-precision2-dBm;
    }
    container output-power {
      description
        "For line system device ports, this value indicates
        the total output optical power of the port in units
        of 0.01dBm. If avg/min/max statistics are not supported,
        just supply the instant value";

      uses oc-types:avg-min-max-instant-stats-precision2-dBm;
    }
  }

  grouping transport-line-common-port-top {
    description
      "Top-level grouping for optical port data";

    container optical-port {
      description
        "Contains data specific to ports on optical transport
        devices.";

        uses transport-line-common-port-config;
        uses oc-mux:frequency-state;
        uses transport-line-common-port-state;

    }
  }



  // data definition statements

  // uses optical-osc-top;

  // augment statements

  //TODO:this is placeholder until SONET model is added
  //to interfaces model

  // rpc statements

  // notification statements

}
