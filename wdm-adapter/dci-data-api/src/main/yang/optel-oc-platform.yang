module optel-oc-platform {

  yang-version "1";

  // namespace
  namespace "com:optel:dci:yang://platform";

  prefix "oc-platform";

  import optel-oc-platform-types { prefix oc-platform-types; }
  import optel-oc-alarm-types { prefix oc-alarm-types; }
  import optel-oc-yang-types { prefix oc-yang; }
  import optel-oc-transport-types { prefix oc-opt-types; }
  import optel-oc-platform-chassis { prefix opt-platform-chassis; }
  import optel-oc-platform-cpu { prefix opt-platform-cpu; }
  import optel-oc-platform-ext { prefix opt-platform-ext; }
  import optel-oc-platform-fan { prefix opt-platform-fan; }
  import optel-oc-platform-foadm { prefix opt-platform-foadm; }
  import optel-oc-platform-linecard { prefix opt-platform-linecard; }
  import optel-oc-platform-mcu { prefix opt-platform-mcu; }
  import optel-oc-platform-mux { prefix opt-platform-mux; }
  import optel-oc-platform-port { prefix opt-platform-port; }
  import optel-oc-platform-psu { prefix opt-platform-psu; }
  import optel-oc-platform-ptm { prefix opt-platform-ptm; }
  import optel-oc-platform-tff { prefix opt-platform-tff; }
  import optel-oc-platform-transceiver { prefix opt-platform-transceiver; }
  import optel-oc-platform-wss { prefix opt-platform-wss; }
  import optel-oc-transport-line-common { prefix oc-line-com; }
  import optel-oc-terminal-device { prefix oc-opt-term; }
  // meta
  organization "OpenConfig working group";

  contact
    "OpenConfig working group
    www.openconfig.net";

  description
    "This module defines a data model for representing a system
    component inventory, which can include hardware or software
    elements arranged in an arbitrary structure. The primary
    relationship supported by the model is containment, e.g.,
    components containing subcomponents.

    It is expected that this model reflects every field replacable
    unit on the device at a minimum (i.e., additional information
    may be supplied about non-replacable components).

    Every element in the inventory is termed a 'component' with each
    component expected to have a unique name and type, and optionally
    a unique system-assigned identifier and FRU number.  The
    uniqueness is guaranteed by the system within the device.

    Components may have properties defined by the system that are
    modeled as a list of key-value pairs. These may or may not be
    user-configurable.  The model provides a flag for the system
    to optionally indicate which properties are user configurable.

    Each component also has a list of 'subcomponents' which are
    references to other components. Appearance in a list of
    subcomponents indicates a containment relationship as described
    above.  For example, a linecard component may have a list of
    references to port components that reside on the linecard.

    This schema is generic to allow devices to express their own
    platform-specific structure.  It may be augmented by additional
    component type-specific schemas that provide a common structure
    for well-known component types.  In these cases, the system is
    expected to populate the common component schema, and may
    optionally also represent the component and its properties in the
    generic structure.

    The properties for each component may include dynamic values,
    e.g., in the 'state' part of the schema.  For example, a CPU
    component may report its utilization, temperature, or other
    physical properties.  The intent is to capture all platform-
    specific physical data in one location, including inventory
    (presence or absence of a component) and state (physical
    attributes or status).";

  revision "2022-02-08" {
    description
      "Added temperature state variable to component";
    reference "0.1.0";
  }

  // grouping statements


  grouping platform-component-properties-config {
    description
      "System-defined configuration data for component properties";

    leaf value {
      type union {
        type string;
        type boolean;
        type int64;
        type uint64;
        type decimal64 {
          fraction-digits 2;
        }
      }
      description
        "Property values can take on a variety of types.  Signed and
        unsigned integer types may be provided in smaller sizes,
        e.g., int8, uint16, etc.";
    }
  }

  grouping platform-component-properties-state {
    description
      "Operational state data for component properties";

    leaf configurable {
      type boolean;
      description
        "Indication whether the property is user-configurable";
    }
  }

  grouping platform-component-properties-top {
    description
      "Top-level grouping ";

    container properties {
      description
        "Enclosing container ";

      list property {
        key "name";
        description
          "List of system properties for the component";

        leaf name {
          type string;
          description
            "Reference to the property name.";
        }

        uses platform-component-properties-config;
        uses platform-component-properties-state;
      }
    }
  }

  grouping platform-subcomponent-ref-top {
    description
      "Top-level grouping for list of subcomponent references";

    container subcomponents {
      description
        "Enclosing container for subcomponent references";

      leaf-list name {
        type string;
        description
          "List of subcomponent references";
      }
    }
  }
  
  grouping supported-vendor-type-state{
    description 
      "Top level for supported vendor type group";
      
    leaf-list supported-vendor-type {
        type string;
        description
        "Vendor defined supported card list.";
    }
  }

  grouping platform-component-config {
    description
      "Configuration data for components";

    leaf name {
     // mandatory true;
      type string;
      description
        "Device name for the component -- this may not be a
        configurable parameter on many implementations.  Where
        component preconfiguration is supported, for example,
        the component name may be configurable.";
    }
    
    leaf admin-state {
      type oc-opt-types:admin-state-type;
      description
          "Sets the admin state of the component";
    }
    
    leaf description {
      type string;
      description
        "System-supplied description of the component";
    }
    
    leaf vendor-type-preconf {
      type string;
      description
        "Preconf type, typecally for slot/card configuration,
        it should be selected from supported-vendor-type";
    } 
  }

  grouping platform-component-state {
    description
      "Operational state data for device components.";

    leaf type {
     // mandatory true;
      type identityref {
          base oc-platform-types:OPENCONFIG_COMPONENT;
      }
     
      description
        "Type of component as identified by the system";
    }
    
    leaf actual-vendor-type {
      type string;
      
      description
        "Actual vendor type for the component.";
    }

    leaf id {
      type string;
      description
        "Unique identifier assigned by the system for the
        component";
    }

    leaf location {
      type string;
      description
        "System-supplied description of the location of the
        component within the system. This could be a bay position,
        slot number, socket location, etc. For component types that
        have an explicit slot-id attribute, such as linecards, the
        system should populate the more specific slot-id.";
    }

    leaf mfg-name {
      type string;
      description
        "System-supplied identifier for the manufacturer of the
        component.  This data is particularly useful when a
        component manufacturer is different than the overall
        device vendor.";
    }

    leaf mfg-date {
      type oc-yang:date;
      description
        "System-supplied representation of the component's
        manufacturing date.";
    }

    leaf hardware-version {
      type string;
      description
        "For hardware components, this is the hardware revision of
        the component.";
    }

    leaf firmware-version {
      type string;
      description
        "For hardware components, this is the version of associated
        firmware that is running on the component, if applicable.";
    }

    leaf software-version {
      type string;
      description
        "For software components such as operating system or other
        software module, this is the version of the currently
        running software.";
    }

    leaf serial-no {
      type string;
      description
        "System-assigned serial number of the component.";
    }

    leaf part-no {
      type string;
      description
        "System-assigned part number for the component.  This should
        be present in particular if the component is also an FRU
        (field replaceable unit)";
    }

    leaf production-num {
      type string;
      description
        "real device part no";
    }

    leaf removable {
      type boolean;
      description
        "If true, this component is removable or is a field
        replaceable unit";
    }

    leaf oper-status {
    //  mandatory true;
      type identityref {
        base oc-platform-types:COMPONENT_OPER_STATUS;
      }
      description
        "If applicable, this reports the current operational status
        of the component.";
    }

    leaf empty {
      type boolean;
      description
        "The empty leaf may be used by the device to indicate that a
        component position exists but is not populated.  Using this
        flag, it is possible for the management system to learn how
        many positions are available (e.g., occupied vs. empty
        linecard slots in a chassis).";
    }

    leaf parent {
      type string;
     // type leafref {
    //    path "../../../component/config/name";
    //  }
      description
        "Reference to the name of the parent component.  Note that
        this reference must be kept synchronized with the
        corresponding subcomponent reference from the parent
        component.";
    }
    
    leaf switch-ability {
      description
       "The capability of optical switcher. For OCM/OTDR only.";
       
      type boolean;
    }
	leaf panel-description {
	  type string;
	  description
	    "port panel name";
	}
    
    // vendor supported type.
    uses supported-vendor-type-state;        
  }

  grouping platform-component-temp-alarm-state {
    description
      "Temperature alarm data for platform components";

    // TODO(aashaikh): consider if these leaves could be in a
    // reusable grouping (not temperature-specific); threshold
    // may always need to be units specific.

    leaf alarm-status {
      type boolean;
      description
        "A value of true indicates the alarm has been raised or
        asserted.  The value should be false when the alarm is
        cleared.";
    }

    leaf alarm-threshold {
      type uint32;
      description
        "The threshold value that was crossed for this alarm.";
    }

    leaf alarm-severity {
      type identityref {
        base oc-alarm-types:OPENCONFIG_ALARM_SEVERITY;
      }
      description
        "The severity of the current alarm.";
    }
  }

  grouping platform-component-power-state {
    description
      "Power-related operational state for device components.";

    leaf allocated-power {
      type uint32;
      units watts;
      description
        "Power allocated by the system for the component.";
    }
    
    leaf rated-power {
      type uint32;
      units watts;
      description
        "Rated power for the component.";
    }

    leaf used-power {
      type uint32;
      units watts;
      description
        "Actual power used by the component.";
    }
  }

  grouping platform-component-temp-state {
    description
      "Temperature state data for device components";

    container temperature {
      description
        "Temperature in degrees Celsius of the component. Values include
        the instantaneous, average, minimum, and maximum statistics. If
        avg/min/max statistics are not supported, the target is expected
        to just supply the instant value";

      uses oc-platform-types:avg-min-max-instant-stats-precision1-celsius;
      uses platform-component-temp-alarm-state;
    }
  }

  grouping platform-component-memory-state {
    description
      "Per-component memory statistics";

    container memory {
      description
        "For components that have associated memory, these values
        report information about available and utilized memory.";

      leaf available {
        type uint64;
        units bytes;
        description
          "The available memory physically installed, or logically
          allocated to the component.";
      }

      // TODO(aashaikh): consider if this needs to be a
      // min/max/avg statistic
      leaf utilized {
        type uint64;
        units bytes;
        description
          "The memory currently in use by processes running on
          the component, not considering reserved memory that is
          not available for use.";
      }
    }
  }

  grouping platform-anchors-top {
    description
      "This grouping is used to add containers for components that
      are common across systems, but do not have a defined schema
      within the optel-oc-platform module.  Containers should be
      added to this grouping for components that are expected to
      exist in multiple systems, with corresponding modules
      augmenting the config/state containers directly.";
    container me {
       uses opt-platform-chassis:chassis-state;
    }
    container chassis {
      description
        "Data for chassis components";
        uses opt-platform-chassis:chassis-config;
        uses opt-platform-chassis:chassis-state;
    }

// TODO(aashaikh): linecard container is already defined in
// optel-oc-platform-linecard; will move to this module
// in future.
  /*
    container linecard {
      description
        "Data for linecard components";
        uses opt-platform-linecard:linecard-top;
    }
  */



// TODO(aashaikh): transceiver container is already defined in
// optel-oc-platform-transceiver; will move to this module
// in future.
  /*
    container transceiver {
      description
        "Data for transceiver components";

      uses opt-platform-transceiver:port-transceiver-top;
    }
  */

    container power-supply {
      description
        "Data for power supply components";

        uses opt-platform-psu:psu-config;
        uses opt-platform-psu:psu-state;
    }

    container fan {
      description
        "Data for fan components";
       uses opt-platform-fan:fan-config;
       uses opt-platform-fan:fan-state;
    }

    container fabric {
      description
        "Data for fabric components";
    }
    
    container mcu {
      description
        "Data for mcu components";

      uses opt-platform-mcu:mcu-state;
    }

    container ptm {
      description
        "Data for ptm components";

        uses opt-platform-ptm:ptm-state;
    }
    
    container mux {
      description
        "Data for mux components";

      uses opt-platform-mux:mux-state;
    }
    container wss {
      description
        "Data for wss components";

      uses opt-platform-wss:wss-state;
    }

    container tff {
      description
        "Data for wss components";

      uses opt-platform-tff:tff-state;
    }
    
    container foadm {
      description
        "Data for foadm components";
       uses opt-platform-foadm:foadm-config;
       uses opt-platform-foadm:foadm-state;
    }

    container storage {
      description
        "Data for storage components";
    }

    container cpu {
      description
        "Data for cpu components";
      uses opt-platform-cpu:component-cpu-utilization;
    }

    container integrated-circuit {
      description
        "Data for chip components, such as ASIC, NPUs, etc.";
    }

    container backplane {
      description
        "Data for backplane components";
    }
  }

  grouping platform-component-top {
    description
      "Top-level grouping for components in the device inventory";

      list component {
        key "name";
        description
          "List of components, keyed by component name.";

        leaf name {
          type string;
          description
            "References the component name";
        }

        container state {

          description
            "Operational state data for each component";

          uses platform-component-config;
          uses platform-component-state;
          uses platform-component-temp-state;
          uses platform-component-memory-state;
          uses platform-component-power-state;
          //augmented from platform-ext
          container platform-ext{
            uses opt-platform-ext:platform-component-ext-state;
          }

        }
        uses platform-component-properties-top;
        uses platform-subcomponent-ref-top;
        uses platform-anchors-top;
        container port{
           uses opt-platform-port:port-breakout-config;
           uses opt-platform-port:port-state;
           uses oc-line-com:transport-line-common-port-top;
        }
        container line-card{
            leaf power-admin-state {
              type oc-platform-types:component-power-type;
            }
        }
        uses opt-platform-transceiver:port-transceiver-top;
        uses oc-opt-term:terminal-optical-channel-top;
      }
  }


  // data definition statements

  // uses platform-component-top;


  // augments

}
