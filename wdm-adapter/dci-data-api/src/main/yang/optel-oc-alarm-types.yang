module optel-oc-alarm-types {

  yang-version "1";

  // namespace
  namespace "com:optel:dci:yang://alarms/types";

  prefix "oc-alarm-types";

  revision "2022-02-08" {
    description
      "Moved alarm identities into separate types module";
  }

  // identity statements
  identity OPENCONFIG_ALARM_TYPE_ID {
    description
      "Base identity for alarm type ID profiles";
  }

  identity AIS {
    base OPENCONFIG_ALARM_TYPE_ID;
    description
      "Defines an alarm indication signal type of alarm";
  }

  identity EQPT {
    base OPENCONFIG_ALARM_TYPE_ID;
    description
      "Defines an equipment related type of alarm that is specific
       to the physical hardware";
  }

  identity LOS {
    base OPENCONFIG_ALARM_TYPE_ID;
    description
      "Defines a loss of signal type of alarm";
  }

  identity OTS {
    base OPENCONFIG_ALARM_TYPE_ID;
    description
      "Defines a optical transport signal type of alarm";
  }

  identity ETH-ALARM {
    base OPENCONFIG_ALARM_TYPE_ID;
    description
      "Defines a ethernet signal type of alarm";
  }

  identity ODUK-ALARM {
    base OPENCONFIG_ALARM_TYPE_ID;
    description
      "Defines a ODUk signal type of alarm";
  }

  identity OTUK-ALARM {
    base OPENCONFIG_ALARM_TYPE_ID;
    description
      "Defines a OTUk signal type of alarm";
  }

  identity OCH-ALARM {
    base OPENCONFIG_ALARM_TYPE_ID;
    description
      "Defines a OCH signal type of alarm";
  }

  identity OP-ALARM {
    base OPENCONFIG_ALARM_TYPE_ID;
    description
      "Defines a optical protection type of alarm";
  }

  identity OA-ALARM {
    base OPENCONFIG_ALARM_TYPE_ID;
    description
      "Defines a optical amplifier type of alarm";
  }

  identity OSC-ALARM {
    base OPENCONFIG_ALARM_TYPE_ID;
    description
      "Defines a optical supervision channel type of alarm";
  }

  identity HARDWARE-ALARM {
    base OPENCONFIG_ALARM_TYPE_ID;
    description
      "Defines a hardware type of alarm";
  }

  identity ENVIRONMENT-ALARM {
    base OPENCONFIG_ALARM_TYPE_ID;
    description
      "Defines a environment type of alarm";
  }

  identity NEIGHBOR-ALARM {
    base OPENCONFIG_ALARM_TYPE_ID;
    description
      "Defines a remote pluggable module type of alarm";
  }

  identity LOCAL-ALARM {
    base OPENCONFIG_ALARM_TYPE_ID;
    description
      "Defines a local pluggable module type of alarm";
  }

  identity OPENCONFIG_ALARM_SEVERITY {
    description
      "Base identity for alarm severity profiles. Derived
      identities are based on contents of the draft
      IETF YANG Alarm Module";
    reference
      "IETF YANG Alarm Module: Draft - typedef severity
      https://tools.ietf.org/html/draft-vallin-netmod-alarm-module-02";

  }

  identity UNKNOWN {
    base OPENCONFIG_ALARM_SEVERITY;
    description
      "Indicates that the severity level could not be determined.
      This level SHOULD be avoided.";
  }

  identity MINOR {
    base OPENCONFIG_ALARM_SEVERITY;
    description
      "Indicates the existence of a non-service affecting fault
      condition and that corrective action should be taken in
      order to prevent a more serious (for example, service
      affecting) fault. Such a severity can be reported, for
      example, when the detected alarm condition is not currently
      degrading the capacity of the resource";
  }

  identity WARNING {
    base OPENCONFIG_ALARM_SEVERITY;
    description
      "Indicates the detection of a potential or impending service
      affecting fault, before any significant effects have been felt.
      Action should be taken to further diagnose (if necessary) and
      correct the problem in order to prevent it from becoming a more
      serious service affecting fault.";
  }

  identity MAJOR {
    base OPENCONFIG_ALARM_SEVERITY;
    description
      "Indicates that a service affecting condition has developed
      and an urgent corrective action is required. Such a severity
      can be reported, for example, when there is a severe
      degradation in the capability of the resource and its full
      capability must be restored.";
  }

  identity CRITICAL {
    base OPENCONFIG_ALARM_SEVERITY;
    description
      "Indicates that a service affecting condition has occurred
      and an immediate corrective action is required. Such a
      severity can be reported, for example, when a resource becomes
      totally out of service and its capability must be restored.";
  }

  typedef alarm-state {
        type enumeration {
            enum start {
                value 0;
                description "alarm-state start";
            }
            enum end {
                value 1;
                description "alarm-state end";
            }
        }
        description "alarm-state";
    }

}
