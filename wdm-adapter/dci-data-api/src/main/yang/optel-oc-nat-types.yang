module optel-oc-nat-types {

  yang-version "1";

  // namespace
  namespace "com:optel:dci:yang://nat-types";

  prefix "oc-nat-types";

  // import some basic types
  import optel-oc-extensions { prefix oc-ext; }


  // meta
  organization "OpenConfig working group";

  contact
    "OpenConfig working group
    www.openconfig.net";

  description
    "This module";

  //oc-ext:openconfig-version "1.0.0";

  revision "2022-06-27" {
    description
      "Initial revision";
    reference "1.0.0";
  }

  // OpenConfig specific extensions for module metadata.

  typedef protocol-type {
    type enumeration {
      enum UDP {
        value 0;
        description
        "type of protocol is UDP";
      }
      enum TCP {
        value 1;
        description
        "type of protocol is TCP";
      }
	  enum ALL {
        value 2;
        description
        "type of protocol supports TCP and UDP";
      }
    }
    description
      "the type of protocol";
    reference "0.1.0";
  }
}
