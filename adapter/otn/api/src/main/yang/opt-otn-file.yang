module opt-otn-file {
    yang-version 1;
    namespace "com:optel:devconf:opt:otn:file";
    prefix "opt-otn-file";

    revision "2021-03-31" {
        description "Initial revision";
    }

    import ietf-yang-types {
        prefix yang;
    }
    import optel-file  {prefix "optel-file"; }
    import base-types  {prefix "base-types";}

    rpc download-file-ne {
        input{
            uses base-types:ne-common-prop;
            leaf file-type {
                mandatory true;
                type optel-file:file-type;
            }
             leaf file-name {
                mandatory true;
                type string;
             }
             leaf file-size {
             mandatory true;
               type uint32;
             }
             leaf path {
                mandatory true;
               type string;
               description "it is fullpath e.g. sftp://ip:port/path/.....";
             }
             leaf username {
                mandatory true;
               type string;
             }
             leaf password {
                mandatory true;
               type string;
             }
        }
    }

    rpc get-file-list-ne{
        input {
            uses base-types:ne-common-prop;
            leaf file-type{
                type string;
                description "data, upgrade, all  如果是all则返回所有类型";
            }
        }
        output{
            list files {
                key 'file-name';
                leaf file-name {
                    type string;
                }
                leaf file-type{
                    type optel-file:file-type;
                }
            }
        }
    }

    rpc upload-file-ne {
        input {
            uses base-types:ne-common-prop;
            leaf file-type {
                mandatory true;
                type optel-file:file-type;
            }
            leaf file-name {
                type string;
                description "如果无此参数，说明是第一次上传，设备需按文件名生成规则生成文件上传并在接口里返回实际上传的文件名";
            }
            leaf path {
                mandatory true;
                type string;
                description "it is fullpath e.g. sftp://ip:port/path/.....";
            }
            leaf username {
                mandatory true;
                type string;
            }
            leaf password {
                mandatory true;
                type string;
            }
        }
        output {
            leaf file-name {
                mandatory true;
                type string;
                description "真正上传的文件名";
            }
            leaf md5 {
                mandatory true;
                type string;
            }
            leaf file-size {
                type uint32;
                description "可选，有能力的话，返回文件大小，字节为单位";
            }
        }
        description "此上传接口仅仅针对配置文件同步上传，要求总时长不超过50秒。升级文件不通过接口上传";
    }

    rpc delete-file-ne {
        input {
            uses base-types:ne-common-prop;
            leaf file-type {
                mandatory true;
                type optel-file:file-type;
            }
            leaf file-name {
                type string;
                mandatory true;
                description "设备判断下发的文件类型和文件名是否匹配，如果不匹配返回错误";
            }
        }
    }

    rpc active-file-ne {
        input {
            uses base-types:ne-common-prop;
            leaf file-type {
                mandatory true;
                type optel-file:file-type;
            }
            leaf file-name {
                type string;
                mandatory true;
                description "设备判断下发的文件类型和文件名是否匹配，如果不匹配返回错误";
            }
        }
    }

    rpc get-active-status-ne {
        input {
            uses base-types:ne-common-prop;
            leaf file-type {
                mandatory true;
                type optel-file:file-type;
            }
        }
        output {
            leaf file-name {
                mandatory true;
                type string;
                description "执行的文件名，方便管控验证是否操作的文件正确";
            }
            leaf active-time {
                type yang:date-and-time;
                description "最终执行active操作后的时间,无论成功还是失败";
            }
            leaf status {
                mandatory true;
                type optel-file:active-status;
            }
            leaf fail-reason {
                type optel-file:fail-reason;
                description "socket-fail, auth-fail,file-not-exist,timeout,validate-fail,upgrade-in-progress,file-type-mismatch";
            }
        }
    }

    rpc get-download-status-ne {
        input {
            uses base-types:ne-common-prop;
            leaf file-type {
                mandatory true;
                type optel-file:file-type;
            }
            leaf file-name {
                type string;
                mandatory true;
                description "设备判断下发的文件类型和文件名是否匹配，如果不匹配返回错误";
            }
        }
        output {
            leaf download-bytes {
                mandatory true;
                type uint32;
                description "已经下载的字节数量";
            }
            leaf status {
               mandatory true;
               type optel-file:download-status;
             }
             leaf fail-reason {
                type optel-file:fail-reason;
               description "socket-fail, auth-fail,file-not-exist,timeout,validate-fail,file-type-mismatch";
             }
        }
    }
}
