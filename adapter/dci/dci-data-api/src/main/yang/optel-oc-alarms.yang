module optel-oc-alarms {

  yang-version "1";

  // namespace
  namespace "com:optel:dci:yang://alarms";

  prefix "oc-alarms";

  // import some basic types
  import optel-oc-alarm-types { prefix oc-alarm-types; }
  import optel-oc-types { prefix oc-types; }
  import optel-oc-yang-types { prefix yang; }

  revision "2022-02-08" {
    description "Initial public release";
  }

  // grouping statements

  grouping alarm-state {
    description
      "Operational state data for device alarms";

    leaf id {
      type string;
      description
        "Unique ID for the alarm -- this will not be a
        configurable parameter on many implementations";
    }

    leaf resource {
      type string;
      description
        "The item that is under alarm within the device. The
        resource may be a reference to an item which is
        defined elsewhere in the model. For example, it
        may be a platform/component, interfaces/interface,
        terminal-device/logical-channels/channel, etc. In this
        case the system should match the name of the referenced
        item exactly. The referenced item could alternatively be
        the path of the item within the model.";
      reference
        "IETF YANG Alarm Module: Draft - typedef resource
        https://tools.ietf.org/html/draft-vallin-netmod-alarm-module-02";
    }

    leaf text {
      type string;
      description
        "The string used to inform operators about the alarm. This
         MUST contain enough information for an operator to be able
         to understand the problem. If this string contains structure,
         this format should be clearly documented for programs to be
         able to parse that information";
      reference
        "IETF YANG Alarm Module: Draft - typedef alarm-text
        https://tools.ietf.org/html/draft-vallin-netmod-alarm-module-02";
    }

    leaf time-created {
      type oc-types:timeticks64;
      description
        "The time at which the alarm was raised by the system.
        This value is expressed relative to the Unix Epoch.";
    }

    leaf end-time {
      type oc-types:timeticks64;
      description
        "The time at which the alarm was end by the system.
        This value is expressed relative to the Unix Epoch.";
    }

    leaf severity {
      type identityref {
        base oc-alarm-types:OPENCONFIG_ALARM_SEVERITY;
      }
      description
        "The severity level indicating the criticality and impact
        of the alarm";
      reference
        "IETF YANG Alarm Module: Draft - typedef severity
        https://tools.ietf.org/html/draft-vallin-netmod-alarm-module-02";
    }

    leaf type-id {
      type union {
        type string;
        type identityref {
          base oc-alarm-types:OPENCONFIG_ALARM_TYPE_ID;
        }
      }
      description
        "The abbreviated name of the alarm, for example LOS,
        EQPT, or OTS. Also referred to in different systems as
        condition type, alarm identifier, or alarm mnemonic. It
        is recommended to use the OPENCONFIG_ALARM_TYPE_ID
        identities where possible and only use the string type
        when the desired identityref is not yet defined";
      reference
        "IETF YANG Alarm Module: Draft - typedef alarm-type-id
        https://tools.ietf.org/html/draft-vallin-netmod-alarm-module-02";
    }
	
    leaf alarm-abbreviate {
      type string;
      description
        "Alarm abbreviate ,refer to related document.";
    }
  }

  grouping alarm-config {
    description
      "Configuration data for device alarms";
  }

  grouping alarms-top {
    description
      "Top-level grouping for device alarms";

    container alarms {
      description
        "Top-level container for device alarms";

      config false;

      list alarm {
        key "id";
        description
          "List of alarms, keyed by a unique id";

        leaf id {
          type leafref {
            path "../state/id";
          }

          description
            "References the unique alarm id";
        }

        container config {
          description
            "Configuration data for each alarm";

          uses alarm-config;
        }

        container state {
          config false;

          description
            "Operational state data for a device alarm";

          uses alarm-config;
          uses alarm-state;
        }
      }
    }
  }

grouping tca {
    leaf alarm-serial-no {
        type string;
        description
            "Unique ID for the alarm -- this will not be a
            configurable parameter on many implementations";
    }

   leaf alarm-state {
        type oc-alarm-types:alarm-state;
        config false;
        description "current tca state";
    }

   leaf start-time {
        config false;
        type yang:date-and-time;
        description "tca start-time";
    }

    leaf end-time {
        config false;
        type yang:date-and-time;
        description "tca end-tiem";
    }

   leaf object-type {
      config false;
      type oc-types:object-type;
        description "tca-parameter object-type";
     }

     leaf object-name {
      config false;
          type string {
              length "1..64";
          }
          description "tca-parameter object-name";
      }

     leaf pm-parameter-name {
      config false;
          type string {
              length "1..64";
          }
          description "tca-parameter pm-parameter-name";
      }

     leaf granularity {
      type oc-types:granularity;
      config false;
      description "tca-parameter granularity";
      }

     leaf threshold-type {
      type oc-types:threshold-type;
      config false;
      description "tca-parameter threshold-type";
      }

     leaf threshold-value {
        type oc-types:real;
        config false;
        description "tca-parameter threshold-value";
    }

     leaf current-value {
        type oc-types:real;
        config false;
            description "tca-parameter threshold-value";
    }
  }

  grouping tcas-top {
      list tca {
          key 'alarm-serial-no';

          uses tca;
          description "tcas list";
      }
      description "tcas";
  }

}
