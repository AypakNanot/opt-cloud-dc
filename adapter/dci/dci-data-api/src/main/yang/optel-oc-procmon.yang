module optel-oc-procmon {

  yang-version "1";

  // namespace
  namespace "com:optel:dci:yang://system/procmon";

  prefix "oc-proc";


  // import some basic types
  import optel-oc-types { prefix oc-types; }
  import optel-oc-yang-types { prefix oc-yang; }


  // meta
  organization "OpenConfig working group";

  contact
    "OpenConfig working group
    www.openconfig.net";

  description
    "This module provides data definitions for process health
    monitoring of one or more processes running on the system.";

  revision "2022-02-08" {
    description
      "Initial public release";
    reference "0.1.0";
  }

  // grouping statements

  grouping procmon-processes-top {
    description
      "Top level grouping for attributes for processes.";

    container processes {
      description
        "Parameters related to all monitored processes";

      list process {
        key "pid";
        config false;
        description
          "List of monitored processes";

        leaf pid {
          type leafref {
            path "../state/pid";
          }
          description
            "Reference to the process pid key";
        }

        container state {
          config false;
          description
            "State parameters related to monitored processes";

          uses procmon-process-attributes-state;
        }
      }
    }
  }

  grouping procmon-process-attributes-state {
    description
      "Attributes state definitions for a process";

    leaf pid {
      type uint64;
      description
        "The process pid";
    }

    leaf name {
      type string;
      description
        "The process name";
    }

    leaf-list args {
      type string;
      description
        "Current process command line arguments.  Arguments with
        a parameter (e.g., --option 10  or -option=10) should be
        represented as a single element of the list with the
        argument name and parameter together.  Flag arguments, i.e.,
        those without a parameter should also be in their own list
        element.";
    }

    leaf start-time {
      type oc-types:timeticks64;
      description
        "The time at which this process started,
        relative to the UNIX epoch.  The system must be
        synchronized such that the start-time can be
        reported accurately, otherwise it should not be reported.";
     }

    leaf cpu-usage-user {
      type oc-yang:counter64;
      units "nanoseconds";
      description
        "CPU time consumed by this process in user mode in
        nanoseconds.";
    }

    leaf cpu-usage-system {
      type oc-yang:counter64;
      units "nanoseconds";
      description
        "CPU time consumed by this process in kernel mode.";
    }

    leaf cpu-utilization {
      type oc-types:percentage;
      description
        "The percentage of CPU that is being used by the process.";
    }

    leaf memory-usage {
      type uint64;
      units "bytes";
      description
        "Bytes allocated and still in use by the process";
    }

    leaf memory-utilization {
      type oc-types:percentage;
      description
        "The percentage of RAM that is being used by the process.";
    }
  }

  // augment statements

  // rpc statements

  // notification statements
}
