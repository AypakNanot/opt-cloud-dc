module optel-oc-platform-cpu {

  yang-version "1";

  // namespace
  namespace "com:optel:dci:yang://platform/cpu";

  prefix "oc-cpu";

  import optel-oc-types { prefix oc-types; }


  // meta
  organization "OpenConfig working group";

  contact
    "OpenConfig working group
    www.openconfig.net";

  description
    "This module defines data related to FAN components in the
    OpenConfig platform model.";

  revision "2022-02-08" {
    description
      "Initial revision";
    reference "0.1.0";
  }

  grouping component-cpu-utilization {
    description
      "Per-component CPU statistics";

    container utilization {
      description
        "Statistics representing CPU utilization of the
        component.";

      uses oc-types:avg-min-max-instant-stats-pct;
    }
  }

}
