module optel-oc-if-poe {

  yang-version "1";

  namespace "com:optel:dci:yang://poe";

  prefix "oc-poe";

  import optel-oc-if-ethernet { prefix oc-eth; }
  import optel-oc-interfaces { prefix oc-if; }

  organization "OpenConfig working group";

  contact
    "Openconfig working group
    www.openconfig.net";

  description
    "This module defines configuration and state data for
    Power over Ethernet (PoE) based on the IEEE 802.3af
    standard.";

  revision "2022-02-08" {
    description
      "Initial public revision";
    reference "0.1.0";
  }

  grouping poe-ethernet-config {
    description
      "PoE ethernet config grouping";

     leaf enabled {
      type boolean;
      description
        "Enable or disable PoE in the ethernet interface.";
    }
  }

  grouping poe-ethernet-state {
    description
      "PoE ethernet state grouping";

    leaf power-used {
      type decimal64 {
        fraction-digits 2;
      }
      units Watts;
      description
        "Power used by the ethernet interface in Watts.";
    }

    leaf power-class {
      type uint8;
      description
        "IEEE 802.3af Power class detected for this ethernet
        interface.";
    }
  }

  grouping poe-ethernet-top {
    description
      "Ethernet top level grouping";

    container poe {
      description
        "Top-level container for PoE configuration and state data";

      container config {
        description
          "Configuration data for PoE";

        uses poe-ethernet-config;
      }

      container state {
        config false;

        description
          "Operational state data for PoE";

        uses poe-ethernet-config;
        uses poe-ethernet-state;
      }
    }
  }

}
