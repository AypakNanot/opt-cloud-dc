module "openconfig-platform-psu" {
  yang-version "1";
  namespace "http://openconfig.net/yang/platform/psu";
  prefix "oc-platform-psu";
  import "openconfig-extensions" {
    prefix "oc-ext";
  }

  import "openconfig-types" {
    prefix "oc-types";
  }

  import "openconfig-platform" {
    prefix "oc-platform";
  }

  import "openconfig-platform-types" {
    prefix "oc-platform-types";
  }

  organization
    "OpenConfig working group";
  contact
    "OpenConfig working group
www.openconfig.net";
  description
    "This module defines a schema for power supply components in
the OpenConfig platform model.";
  revision "2020-06-30" {
    description
      "Initial release for DCI Box.";
    reference
      "0.2.2";
  }

  revision "2018-11-21" {
    description
      "Add OpenConfig module metadata extensions.";
    reference
      "0.2.1";
  }

  revision "2018-01-16" {
    description
      "Changed admin state leaf name";
    reference
      "0.2.0";
  }

  revision "2017-12-21" {
    description
      "Initial revision";
    reference
      "0.1.0";
  }

  grouping "psu-config" {
    description
      "Configuration data for power supply components";
  }

  grouping "psu-state" {
    description
      "Operational state data for power supply components";
    leaf "enabled" {
      type "boolean";
      default "true";
      description
        "Adminsitrative control on the on/off state of the power
supply unit.";
    }

    leaf "capacity" {
      type "decimal64" {
        fraction-digits "2";
      }

      units "watts";
      description
        "Maximum power capacity of the power supply.";
    }

    leaf "input-current" {
      type "decimal64" {
        fraction-digits "2";
      }

      units "mA";
      description
        "The input current draw of the power supply.";
    }

    leaf "input-voltage" {
      type "decimal64" {
        fraction-digits "2";
      }

      units "volts";
      description
        "Input voltage to the power supply.";
    }

    leaf "output-current" {
      type "decimal64" {
        fraction-digits "2";
      }

      units "mA";
      description
        "The output current supplied by the power supply.";
    }

    leaf "output-voltage" {
      type "decimal64" {
        fraction-digits "2";
      }

      units "volts";
      description
        "Output voltage supplied by the power supply.";
    }

    leaf "output-power" {
      type "decimal64" {
        fraction-digits "2";
      }

      units "watts";
      description
        "Output power supplied by the power supply.";
    }

    container "supported-power-supply-modes" {
      leaf-list "supported-power-supply-mode" {
        type "oc-platform-types:psu-mode-type";
        description
          "Reference to supported mode";
      }

    }

    leaf "used-power-supply-mode" {
      type "oc-platform-types:psu-mode-type";
      description
        "Output power supplied by the power supply.";
    }

  }

  augment "/oc-platform:components/oc-platform:component/oc-platform:power-supply/oc-platform:config" {
    description
      "Adds power supply data to component operational state.";
    uses "psu-config" {
      when "../oc-platform:state/oc-platform:type = 'POWER_SUPPLY'" {
        description
          "This data is valid only for POWER_SUPPLY components";
      }

    }

  }

  augment "/oc-platform:components/oc-platform:component/oc-platform:power-supply/oc-platform:state" {
    description
      "Adds power supply data to component operational state.";
    uses "psu-config" {
      when "../oc-platform:state/oc-platform:type = 'POWER_SUPPLY'" {
        description
          "This data is valid only for POWER_SUPPLY components";
      }

    }

    uses "psu-state" {
      when "../oc-platform:state/oc-platform:type = 'POWER_SUPPLY'" {
        description
          "This data is valid only for POWER_SUPPLY components";
      }

    }

  }

}
