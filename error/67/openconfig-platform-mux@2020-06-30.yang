module "openconfig-platform-mux" {
  yang-version "1";
  namespace "http://openconfig.net/yang/platform/mux";
  prefix "oc-mux";
  import "openconfig-platform" {
    prefix "oc-platform";
  }

  import "openconfig-platform-types" {
    prefix "oc-platform-types";
  }

  import "openconfig-extensions" {
    prefix "oc-ext";
  }

  organization
    " working group";
  contact
    "  working group";
  description
    "This module defines data related to mux components in
the openconfig-platform model";
  revision "2020-06-30" {
    description
      "Initial revision";
    reference
      "0.1.0";
  }

  grouping "mux-config" {
    description
      "Configuration data for mux components";
  }

  grouping "mux-state" {
    description
      "Operational state data for mux components";
    leaf "channel-interval" {
      type "oc-platform-types:channel-interval-type";
      description
        "channel interval, 50/75/100GHz";
    }

    leaf "support-flex-grid" {
      type "boolean";
      description
        "Support flex grid status for mux components";
    }

    leaf "channel-num" {
      type "uint32";
      description
        "The channel number for the mux, example 44,96";
    }

  }

  augment "/oc-platform:components/oc-platform:component/oc-platform:mux/oc-platform:state" {
    description
      "Adding mux state data";
    uses "mux-state";
  }

}
