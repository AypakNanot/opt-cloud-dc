module acc-notifications {
    yang-version 1.1;
    namespace "urn:ccsa:yang:acc-notifications";
    prefix acc-ntf;

    revision 2021-09-24 {
        description "uniform date for motn";
    }
    /*
    * Common types
    */
    typedef event-type {
        type enumeration {
            enum object-creation {
                value 0;
            }
            enum object-deletion {
                value 1;
            }
            enum attribute-value-change {
                value 2;
            }
            enum user-login {
                value 3;
            }
            enum user-logoff {
                value 4;
            }
        }
    }   
    /*
    * Groupings
    */    
    grouping event {
        leaf event-serial-no {
            mandatory true;
            type uint64;
        }
        leaf event-type {
            mandatory true;
            type event-type;
        }
        leaf object-name {
            mandatory true;
            type string;
        }
        leaf object-type {
            mandatory true;
            type string;
        }
        leaf user-name {
            type string;
        }
    }

    /*
    * Notifications
    */    
    notification common-notification {
        container event {
            uses event;
        }
    }

    notification attribute-value-change-notification {
        container event {
            uses event;
        }
        container attribute-value-change {
            leaf attribute-name {
                mandatory true;
                type string;
            }
            leaf new-value {
                mandatory true;
                type string;
            }
            leaf old-value {
                type string;
            }
        }
    }

    notification ems-oper-notification {
        leaf category {
            mandatory true;
            type string;
            description "必填，大类别：CONNECTION/PG/TP/ALARM/PM/ME";
        }
        leaf object-type {
            type string;
            description "可选，详细类别：ETH/VC/ODU/OSU/PTP/FTP/CTP";
        }
        leaf object-name {
            type string;
            description "可选，具体对象名，category为CONNECTION，PG，TP相关重要类别时，必须上报";
        }
        leaf oper-type {
            mandatory true;
            type string;
            description "必填，默认操作类型： change，如果能分清具体类型，则使用add or update or delete";
        }
        leaf oper-detail{
            mandatory true;
            type string;
            description "必填，具体操作内容，没有固定格式，可使用英文或者中文简单描述";
        }
    }

}
