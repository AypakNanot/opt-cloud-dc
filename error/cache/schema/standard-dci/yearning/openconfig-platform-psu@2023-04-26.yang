module openconfig-platform-psu {

  yang-version "1";

  // namespace
  namespace "http://openconfig.net/yang/platform/psu";

  prefix "oc-platform-psu";

  // import some basic types
  import openconfig-extensions { prefix oc-ext;revision-date "2018-10-17"; }
  import openconfig-types { prefix oc-types;revision-date "2023-04-26"; }
  import openconfig-platform { prefix oc-platform;revision-date "2023-04-26"; }
  import openconfig-platform-types { prefix oc-platform-types;revision-date "2023-04-26"; }


  // meta
  organization "OpenConfig working group";

  contact
    "OpenConfig working group
    www.openconfig.net";

  description
    "This module defines a schema for power supply components in
    the OpenConfig platform model.";

  oc-ext:openconfig-version "0.2.1";

  revision "2023-04-26" {
    description
      "Initial release for MinOTN.";
    reference "0.2.2";
  }
  
  revision "2018-11-21" {
    description
      "Add OpenConfig module metadata extensions.";
    reference "0.2.1";
  }

  revision "2018-01-16" {
    description
      "Changed admin state leaf name";
    reference "0.2.0";
  }

  revision "2017-12-21" {
    description
      "Initial revision";
    reference "0.1.0";
  }

  // OpenConfig specific extensions for module metadata.
  oc-ext:regexp-posix;
  oc-ext:catalog-organization "openconfig";
  oc-ext:origin "openconfig";

  // identity statements

  // typedef statements

  // grouping statements

  grouping psu-config {
    description
      "Configuration data for power supply components";

  }

  grouping psu-state {
    description
      "Operational state data for power supply components";

    leaf enabled {
      //mandatory true;
      type boolean;
      default true;
      description
        "Adminsitrative control on the on/off state of the power
        supply unit.";
    }
    
    // TODO(aashaikh): May need to convert some of these to
    // interval statistics once decided on which leaves to include.
    leaf capacity {
      //mandatory true;
      type decimal64{
        fraction-digits 2;
      }
      units watts;
      description
        "Maximum power capacity of the power supply.";
    }

    leaf input-current {
     // mandatory true;
      type decimal64{
        fraction-digits 2;
      }
      units mA;
      description
        "The input current draw of the power supply.";
    }

    leaf input-voltage {
     // mandatory true;
      type decimal64{
        fraction-digits 2;
      }
      units volts;
      description
        "Input voltage to the power supply.";
    }

    leaf output-current {
      //mandatory true;
      type decimal64{
        fraction-digits 2;
      }
      units mA;
      description
        "The output current supplied by the power supply.";
    }

    leaf output-voltage {
     // mandatory true;
      type decimal64{
        fraction-digits 2;
      }
      units volts;
      description
        "Output voltage supplied by the power supply.";
    }

    leaf output-power {
      type decimal64{
        fraction-digits 2;
      }
      units watts;
      description
        "Output power supplied by the power supply.";
    }
    
    container supported-power-supply-modes {
        leaf-list supported-power-supply-mode {
          //min-elements 1;
          type oc-platform-types:psu-mode-type;
          description
               "Reference to supported mode";          
        }
    }
    
    leaf used-power-supply-mode {
      type oc-platform-types:psu-mode-type; 
      description
        "Output power supplied by the power supply.";
    }
  }

  // data definition statements

  // augment statements

  augment "/oc-platform:components/oc-platform:component/" +
    "oc-platform:power-supply/oc-platform:config" {
    description
      "Adds power supply data to component operational state.";

    uses psu-config{
      when "../oc-platform:state/oc-platform:type = 'POWER_SUPPLY'" {
        description
          "This data is valid only for POWER_SUPPLY components";
      }
    }
  }

  augment "/oc-platform:components/oc-platform:component/" +
    "oc-platform:power-supply/oc-platform:state" {
    description
      "Adds power supply data to component operational state.";

    uses psu-config{
      when "../oc-platform:state/oc-platform:type = 'POWER_SUPPLY'" {
        description
          "This data is valid only for POWER_SUPPLY components";
      }
    }
    uses psu-state{
      when "../oc-platform:state/oc-platform:type = 'POWER_SUPPLY'" {
        description
          "This data is valid only for POWER_SUPPLY components";
      }
    }
  }


  // rpc statements

  // notification statements
}
