module openconfig-platform-fan {

  yang-version "1";

  // namespace
  namespace "http://openconfig.net/yang/platform/fan";

  prefix "oc-fan";

  import openconfig-platform { prefix oc-platform;revision-date "2023-04-26"; }
  import openconfig-extensions { prefix oc-ext;revision-date "2018-10-17"; }
  import openconfig-platform-types { prefix oc-platform-types;revision-date "2023-04-26"; }


  // meta
  organization "OpenConfig working group";

  contact
    "OpenConfig working group
    www.openconfig.net";

  description
    "This module defines data related to FAN components in the
    OpenConfig platform model.";

  oc-ext:openconfig-version "0.1.1";

  revision "2023-04-26" {
    description
      "Initial release for MinOTN.";
    reference "0.1.2";
  }
  
  revision "2018-11-21" {
    description
      "Add OpenConfig module metadata extensions.";
    reference "0.1.1";
  }

  revision "2018-01-18" {
    description
      "Initial revision";
    reference "0.1.0";
  }

  // OpenConfig specific extensions for module metadata.
  oc-ext:regexp-posix;
  oc-ext:catalog-organization "openconfig";
  oc-ext:origin "openconfig";

  // identity statements

  // typedef statements

  // grouping statements

  grouping fan-config {
    description
      "Operational config data for fan components";

    leaf fan-mode {
      //TODO: mandatory true;
      type oc-platform-types:fan-mode-type;
      description
        "Sets fan mode";
    }
    
    leaf fan-speed {
      //TODO: mandatory true;
      type oc-platform-types:fan-speed-type;
      description
        "Sets fan speed";
    }
  }
  
  grouping fan-state {
    description
      "Operational state data for fan components";
    
  }


  // data definition statements

  // augment statements

  augment "/oc-platform:components/oc-platform:component/" +
    "oc-platform:fan/oc-platform:config" {
    description
      "Adding fan data to component model";

    uses fan-config; 
  }
  
  augment "/oc-platform:components/oc-platform:component/" +
    "oc-platform:fan/oc-platform:state" {
    description
      "Adding fan data to component model";

    uses fan-config;
    uses fan-state;
  }

}
