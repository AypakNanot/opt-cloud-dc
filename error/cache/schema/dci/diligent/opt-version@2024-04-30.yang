module "opt-version" {
  yang-version "1.1";
  namespace "com:opt:dci:diligent:yang:version";
  prefix "opt-ver";
  revision "2024-04-30" {
    description
      "This revision change history:
- 2024-04-11 new versioning file for publishing
- 2024-04-12 add serial number as licenses key
";
  }

}
