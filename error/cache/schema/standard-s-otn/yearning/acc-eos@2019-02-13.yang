module acc-eos {
    yang-version 1.1;
    namespace "urn:ccsa:yang:acc-eos";
    prefix acc-eos;

    import acc-devm { 
        prefix acc-devm;
        revision-date "2020-07-08";
    }
    import acc-eth {
        prefix acc-eth;
        revision-date "2020-06-11";
    }
    import acc-sdh {
        prefix acc-sdh;
        revision-date "2020-07-08";
    }
    import acc-connection {
        prefix acc-con;
        revision-date "2020-02-09";
    }
    import acc-otn {
        prefix acc-otn;
        revision-date "2020-07-08";
    }

    import acc-otn-types {
        prefix acc-otn-types;
    }

    import acc-protection-group {
        prefix acc-pg;
        revision-date "2020-07-08";
    }
    

    revision 2019-02-13 {
        description
            "Initial revision.";
        reference
            "xxx";
    }

    augment "/acc-devm:ftps/acc-devm:ftp/acc-eth:eth-ftp-pac" {
        when "acc-eth:mapping-type = 'EoS'";
        container vcg-parameters {
            uses acc-sdh:vcg-pac;
            description "Virtual concatenation group";
        }
    }
	
    rpc create-eos-connection {
        input {
            uses acc-con:create-connection;
            leaf service-mapping-mode {
                type identityref{
                    base acc-otn-types:adaptation-type;
                }
                description "基于SDH FTP客户信号类型，STM-1/STM-4=GMP，STM-16/STM-64=CBR_BMP";
            }
            leaf uni-protection-type {
                type acc-pg:protection-type;
                description "default lag";
            }
            container eth-uni {
                leaf uni-ptp-name {
                    type string;
                }
                leaf second-uni-ptp-name {
                    type string;
                    description "可选，用于与客户设备之间建立LAG保护（非负载均衡，单端保护）";
                }
				container client-vlan-spec {
					when "../../service-type = 'EVPL'";
						uses acc-con:vlan-spec;
						description "只适用于EVPL，指定C-VLAN，用于客户Vlan与运营商Vlan的匹配，无需携带accessAction。不携带该参数时表示端口匹配";
                }
				container uni-vlan-spec {
					when "../../service-type = 'EVPL'";
						uses acc-con:vlan-spec;
						description "用于在客户VLAN交换的情况下，指定C-VLAN的交换值，类型为C-TAG，可选.";
                }
            }
            uses nni-grouping;
        }
        output {
            container connection {
                uses acc-con:connection;
            }
            container create-component {
                leaf-list vc-connection-name {
                    type string;
                    min-elements 0;
                }
                leaf-list ftp-name {
                    type string {
                        length "1..64";
                    }
                }
                leaf-list ctp-name {
                    type string {
                        length "1..64";
                    }
                }              
            }
        }
    }

    grouping nni-grouping{
        leaf nni-protection-type {
            type acc-pg:protection-type;
        }
        leaf nni-tcm {
            type uint16;
            description "when nni-protection-type = 'snc-s', needs to be issued to present the nni tcm of both work path and protection path";
        }
        container primary-nni {
            uses acc-otn:nni;
			description "ptp是ODU层协议时，nni参数中的nni-ts-detail、adaptation-type、odu-signal-type、switch-capability这几个参数必填，否则不用填";
            container ftp-client-vlan-spec {
                uses acc-con:vlan-spec;
                description "";
            }
            container ftp-vlan-spec {
                uses acc-con:vlan-spec;
                description "EVPL必须下发，对于其他业务可选，accessAction=PUSH_POP";
            }
            leaf tpid {
                type acc-eth:tpid-difinition;
            }
        }
        container secondary-nni {
            uses acc-otn:nni;
			description "ptp是ODU层协议时，nni参数中的nni-ts-detail、adaptation-type、odu-signal-type、switch-capability这几个参数必填,否则不用填";
            container ftp-client-vlan-spec {
                uses acc-con:vlan-spec;
                description "";
            }
            container ftp-vlan-spec {
                uses acc-con:vlan-spec;
                description "EVPL必须下发，对于其他业务可选，accessAction=PUSH_POP";
            }
        }

        container eos-pac {
            leaf sdh-signal-type {
                type identityref {
                    base acc-otn-types:client-signal-type;
                }
            }
            leaf vc-type {
                mandatory true;
                type identityref {
                    base acc-otn-types:switch-type;
                }
            }
            leaf-list mapping-path {
                min-elements 1;
                type string {
                    length "1..64";
                }
            }
            leaf sdh-signal-type-protect {
                type identityref {
                    base acc-otn-types:client-signal-type;
                }
            }
            leaf-list mapping-path-protect {
                type string {
                    length "1..64";
                }
            }
            leaf lcas {
                type boolean;
                default false;
            }
            leaf hold-off {
                type uint32;
                default 0;
                description "unit: ms";
            }
            leaf wtr {
                type uint32;
                default 300;
                description "unit: s";
            }
            leaf tsd {
                type boolean;
                default false;
            }
			description "EoS属性";
        }
        container multi-nni-pac{
            list nnis{
                key 'nni-ptp-name nni-ts-detail vcg-key';
                uses multi-nni-grouping;
            }
            description "多路径业务时,传入此参数。此时primary-nni和secondary-nni不填";
        }
        container multi-secondary-nni {
            list secondary-nnis {
                key 'nni-ptp-name nni-ts-detail vcg-key';
                uses multi-nni-grouping;
                leaf nni-protection-type {
                   type acc-pg:protection-type;
                   description "指定保护类型";
                }
                container primary-attr {
                    leaf nni-ptp-name {
                        type string{
                           length "1..64";
                        }
                    }
                    leaf nni-ts-detail {
                        type string{
                           length "1..64";
                        }
                    }
                    leaf vcg-key {
                        type string {
                            length "1..64";
                        }
                        description "填VC占用列表中的第一个mappingPath值";
                    }
                    description "指定被保护的主用信息";
                }
            }
            description "用于多路径业务备用属性配置。可选";
         }
         container lcas-attr {
             uses lcas-attr-grouping;
             description "用于多路径业务的LCAS属性参数。当配置多路径业务时必填，否则不填。";
         }
		 container multi-svlan-attr{
			container ftp-client-vlan-spec {
				 uses acc-con:vlan-spec;
				 description "";
			 }
			 container ftp-vlan-spec {
				 uses acc-con:vlan-spec;
				 description "当需要打上或剖离SVLAN标签的EVPL业务时，必须下发，对于其他业务可选，accessAction=PUSH_POP";
			 }	
			 leaf tpid {
				 type acc-eth:tpid-difinition;
			 }
			 description "用于多路径业务的S-VLAN属性参数。当配置多路径业务时可选";
		 }
    }

    grouping multi-nni-grouping {
         uses acc-otn:nni;
         leaf sdh-signal-type {
             type identityref {
                 base acc-otn-types:client-signal-type;
             }
         }
         leaf vc-type {
             mandatory true;
             type identityref {
                 base acc-otn-types:switch-type;
             }
         }
         leaf vcg-key {
             type string {
                 length "1..64";
             }
             description "填VC占用列表中的第一个mappingPath值";
         }
         leaf-list mapping-path {
             min-elements 1;
             type string {
                 length "1..64";
             }
         }
         description "多路径线路侧参数,ptp是ODU层协议时，nni参数中的nni-ts-detail、adaptation-type、odu-signal-type、switch-capability这几个参数必填，否侧除nni-ts-detail固定填字符串“0”外，其它参数都不用填";
    }

    grouping lcas-attr-grouping{
         leaf lcas {
              type boolean;
              default false;
          }
          leaf hold-off {
              type uint32;
              default 0;
              description "unit: ms";
          }
          leaf wtr {
              type uint32;
              default 300;
              description "unit: s";
          }
          leaf tsd {
              type boolean;
              default false;
          }
    }

    rpc modify-vcg-connection-capacity {
        input {
            leaf eth-ftp-name {
                mandatory true;
                type string {
                    length "1..64";
                }
                description
                    "The name of eth ftp name.";
            }
            leaf sdh-ftp-name {
                mandatory true;
                type string {
                    length "1..64";
                }
                description
                    "The name of sdh ftp name or sdh ptp name";
            }
            leaf sdh-protect-ftp-name {
                type string {
                    length "1..64";
                }
                description
                    "The name of the protect sdh ftp name or sdh ptp name.";
            }
            leaf-list mapping-path {
                min-elements 1;
                type string {
                    length "1..64";
                }
                description
                    "The mapping path list.";
            }
            leaf-list mapping-path-protected {
                type string {
                    length "1..64";
                }
                description
                    "The protected mapping path list.";
            }
        }
        output {
            leaf-list connection-name {
                type string;
            }
            leaf-list ctp-name {
                type string {
                    length "1..64";
                }
            }
        }
    }
}
