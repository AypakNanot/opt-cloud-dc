module acc-performance {
    yang-version 1.1;
    namespace "urn:ccsa:yang:acc-performance";
    prefix acc-pm;

    import ietf-yang-types {
        prefix yang;
    }
    import acc-yang-types {
        prefix acc-type;
    }
    
    organization "xxx";
    contact "xxx";
    description "This module defines an interface for managing performances.";
    
	revision 2021-01-31 {
        description "for M-OTN 1.0";
    }
    /*
    * Groupings
    */   
    grouping performances-grouping {
        list performance {
            config false;
            key 'object-name pm-parameter-name granularity start-time';
            leaf object-name {
                type string {
                    length "1..64";
                }
                description "object-name";
            }
            leaf pm-parameter-name {
                type string {
                    length "1..64";
                }
                description "pm-parameter-name";
            }
            leaf granularity {
                type acc-type:granularity;
                description "granularity";
            }
            leaf start-time {
                type yang:date-and-time;
                description "start-time";
            }
            leaf object-type {
                mandatory true;
                type string {
                    length "1..64";
                }
                description "object-type";
            }
            choice digital-or-analog  {
				config false;
                case digital {
                  leaf digital-pm-value {
                    type acc-type:real;
                    description "digital-pm-value";
                    }
                }
                case analog {
                    container analog-pm-value {
                        leaf max-value {
                            type acc-type:real;
                            description "max-value";
                        }
                        leaf min-value {
                            type acc-type:real;
                            description "min-value";
                        }
                        leaf average-value {
                            type acc-type:real;
                            description "average-value";
                        }
                        leaf current-value {
                            type acc-type:real;
                            description "current-value 查询历史性能中不需要";
                        }
                        description "analog-pm-value";
                    }
                }
            }
            description "performance list";
        }
        description "performances";
    }

    grouping pm-states {
        list pm-state {
            key 'object-name pm-parameter-name granularity';
            leaf object-name {
                type string {
                    length "1..64";
                }
                description "object-name";
            }
            leaf pm-parameter-name {
                type string;
                description "pm-parameter-name";
            }
            leaf granularity {
                type acc-type:granularity;
                description "15min 24h";
            }
            leaf object-type {
                type string;
                description "ME,EQ,PTP";
            }
            leaf pm-state {
                type boolean;
                description "";
            }
        }   
    }
    /*
    * The data tree
    */
    container performances {
        uses performances-grouping;
        description "performances container";
    }

    
    /*
    * Operations
    */
    rpc get-history-performance-monitoring-data {
            input {
                leaf start-time {
                    mandatory true;
                    type yang:date-and-time;
                }
                leaf end-time {
                    mandatory true;
                    type yang:date-and-time;
                }
                leaf object-name {
                    type string {
                        length "1..64";
                    }
                }
                leaf granularity {
                    type acc-type:granularity;
                }
                leaf pm-parameter-name {
                    type string {
                        length "1..64";
                    }
                }
            }
            output {
                container performances {
                    uses performances-grouping;
                } 
            }
    }
    rpc set-pm-state {
            input {
                
                leaf object-name {
                    mandatory true;
                    type string {
                        length "1..64";
                    }
                    description "支持网元，端口。 EQ（可选如果支持）";
                }
                leaf object-type {
                    mandatory true;
                    type string;
                }
                leaf include-sub-obj {
                    type boolean;
                    description "可选，是否对当前object-name下的子对象也进行设置，默认false";
                }
                leaf granularity {
                    type acc-type:granularity;
                }
                leaf pm-parameter-name {
                    type string;
                }
                leaf pm-state {
                    mandatory true;
                    type boolean;
                }
            }
            
            description "具体规则查看企标描述";
    }

    rpc get-all-pm-state {
        input {
            leaf object-name {
                mandatory true;
                type string {
                    length "1..64";
                }
                description "支持网元，端口。 EQ（可选如果支持）";
            }
            leaf object-type {
                mandatory true;
                type string;
            }
            leaf include-sub-obj {
                type boolean;
                description "可选，是否对当前object-name下的子对象也进行设置，默认false";
            }
            leaf granularity {
                type acc-type:granularity;
            }
            leaf pm-parameter-name {
                type string;
            }
        }
        output {
            leaf report-policy{
                type string;
                description "open or close or all 如果为open，则只上报打开的性能开关，如果为close，则只上报关闭的性能开关。如果为all则全部上报，默认不返回此字段，即为all。 按端口查询必须为all，按网元查询可根据设备实际情况选择";
            }
            container pm-states {
                uses pm-states;
                description "performances states";
            }
        }
    }
}
