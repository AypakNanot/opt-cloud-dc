module "openconfig-platform-chassis" {
  yang-version "1";
  namespace "http://openconfig.net/yang/platform/chassis";
  prefix "oc-chassis";
  import "openconfig-platform" {
    prefix "oc-platform";
  }

  import "openconfig-platform-types" {
    prefix "oc-platform-types";
  }

  import "openconfig-extensions" {
    prefix "oc-ext";
  }

  organization
    " working group";
  contact
    "  working group";
  description
    "This module defines data related to chassis components in
the openconfig-platform model";
  revision "2020-06-30" {
    description
      "Initial revision";
    reference
      "1.7.2";
  }

  grouping "chassis-config" {
    description
      "Configuration data for chassis components";
    leaf "lcd" {
      type "string";
      description
        "Sets the lcd content";
    }

  }

  grouping "chassis-state" {
    description
      "Operational state data for chassis components";
    leaf "chassis-type" {
      type "oc-platform-types:component-chassis-type";
      description
        "Chassis type for chassis components";
    }

  }

  augment "/oc-platform:components/oc-platform:component/oc-platform:chassis/oc-platform:config" {
    description
      "Adding chassis data to physical inventory";
    uses "chassis-config";
  }

  augment "/oc-platform:components/oc-platform:component/oc-platform:chassis/oc-platform:state" {
    description
      "Adding chassis state data";
    uses "chassis-config";
    uses "chassis-state";
  }

}
