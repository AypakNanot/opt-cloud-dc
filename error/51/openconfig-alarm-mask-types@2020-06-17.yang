module "openconfig-alarm-mask-types" {
  yang-version "1";
  namespace "http://openconfig.net/yang/alarms/mask/types";
  prefix "oc-alarm-mask-types";
  import "openconfig-extensions" {
    prefix "oc-ext";
  }

  organization
    "OpenConfig working group";
  contact
    "OpenConfig working group
www.openconfig.net";
  description
    "This module";
  revision "2020-06-17" {
    description
      "Initial revision";
    reference
      "1.0.0";
  }

  typedef "alarm-object-type" {
    type "enumeration" {
      enum "CHASSIS" {
        value "0";
        description
          "range of alarm mask is a chassis";
      }

      enum "CARD" {
        value "1";
        description
          "range of alarm mask is a card";
      }

      enum "PORT" {
        value "2";
        description
          "range of alarm mask is a port";
      }

    }

    description
      "the range of alarm mask";
    reference
      "0.1.0";
  }

}
